module example-newco-bgp {
  yang-version 1.1;
  namespace "http://example.com/ns/example-newco-bgp";
  prefix example-newco-bgp;

  import ietf-routing {
    prefix rt;
    reference
      "RFC 8349, A YANG Data Model for Routing Management
       (NMDA Version)";
  }

  import ietf-bgp {
    prefix "bgp";
  }

  organization
    "Newco model group.";

  contact
    "abc@example.com";
  description
    "This YANG module deviates IETF BGP YANG module.";

  revision YYYY-MM-DD {
    description
      "Creating NewCo deviations to ietf-bgp model";

    reference
      "RFC XXXX: YANG module for Border Gateway Protocol (BGP).";
  }

  deviation "/rt:routing/rt:control-plane-protocols/" +
            "rt:control-plane-protocol/bgp:bgp/bgp:global/" +
            "bgp:graceful-restart/bgp:restart-time" {
    deviate not-supported;
  }

  deviation "/rt:routing/rt:control-plane-protocols/" +
            "rt:control-plane-protocol/bgp:bgp/bgp:global/" +
            "bgp:graceful-restart/bgp:stale-routes-time" {
    deviate not-supported;
  }
}
