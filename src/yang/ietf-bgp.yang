module ietf-bgp {
  yang-version 1.1;
  namespace "urn:ietf:params:xml:ns:yang:ietf-bgp";
  prefix bgp;

  /*
   * Import and Include
   */

  import ietf-routing {
    prefix rt;
    reference
      "RFC 8349: A YANG Data Model for Routing Management
       (NMDA Version).";
  }
  import ietf-routing-policy {
    prefix rt-pol;
    reference
      "RFC 9067: A YANG Data Model for Routing Policy.";
  }
  import ietf-bgp-types {
    prefix ibt;
    reference
      "RFC XXXX: YANG Model for Border Gateway Protocol (BGP-4).";
  }
  import ietf-inet-types {
    prefix inet;
    reference
      "RFC 9911: Common YANG Data Types.";
  }
  import ietf-yang-types {
    prefix yang;
    reference
      "RFC 9911: Common YANG Data Types.";
  }
  import ietf-yang-semver {
    prefix ysv;
    reference
      "I-D.ietf-netmod-yang-semver: YANG Semantic Versioning";
  }
  include ietf-bgp-capabilities {
    revision-date YYYY-MM-DD;
  }
  include ietf-bgp-common {
    revision-date YYYY-MM-DD;
  }
  include ietf-bgp-common-errors {
    revision-date YYYY-MM-DD;
  }
  include ietf-bgp-common-multiprotocol {
    revision-date YYYY-MM-DD;
  }
  include ietf-bgp-neighbor {
    revision-date YYYY-MM-DD;
  }
  include ietf-bgp-rib {
    revision-date YYYY-MM-DD;
  }
  include ietf-bgp-rib-attributes {
    revision-date YYYY-MM-DD;
  }
  include ietf-bgp-rib-tables {
    revision-date YYYY-MM-DD;
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This module describes a YANG model for BGP protocol
     configuration. It is a limited subset of all of the
     configuration parameters available in the variety of vendor
     implementations, hence it is expected that it would be augmented
     with vendor-specific configuration data as needed. Additional
     modules or submodules to handle other aspects of BGP
     configuration, including policy, VRFs, VPNs, and additional
     address families are also expected.

     This model supports the following BGP configuration level
     hierarchy:

      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    ysv:version 0.0.9;
    reference
      "RFC XXXX: YANG Model for Border Gateway Protocol (BGP-4).";
  }

  /*
   * Identity
   */

  identity bgp {
    base rt:routing-protocol;
    description
      "BGP protocol.";
  }

  /*
   * Containers
   */

  augment "/rt:routing/rt:control-plane-protocols/"
        + "rt:control-plane-protocol" {
    when "derived-from-or-self(rt:type, 'bgp')" {
      description
        "This augmentation is valid for a routing protocol
         instance of BGP.";
    }
    description
      "BGP protocol augmentation of ietf-routing module
       control-plane-protocol.";
    container bgp {
      description
        "Top-level configuration for the BGP router.";
      container global {
        presence "Enables global configuration of BGP.";
        description
          "Global configuration for the BGP router.";
        leaf as {
          type inet:as-number;
          mandatory true;
          description
            "Local autonomous system number of the router.  Uses
             the 32-bit as-number type from the model in RFC 9911.";
        }
        leaf treat-as-withdraw {
          type boolean;
          description
            "Specify whether erroneous UPDATE messages for which the
             NLRI can be extracted are treated as though the NLRI is
             withdrawn - avoiding session reset.  The suggested
             implementation default is true.";
          reference
            "RFC 7606: Revised Error Handling for BGP UPDATE
             Messages.";
        }
        leaf enforce-first-as {
           type boolean;
           description
             "When set to true, the leftmost AS in the AS_PATH of BGP
              UPDATE messages received from external peers MUST be
              equal to autonomous system number of the peer that sent
              the message.

              If the check determines they are not equal and
              treat-as-withdraw is false, a BGP NOTIFICATION is sent.
              If treat-as-withdraw is true, the routes will be
              withdraw without and no NOTIFICATION is sent.";
           reference
             "RFC 4271: A Border Gateway Protocol 4 (BGP-4),
              Section 6.3.
              RFC 7606: Revised Error Handling for BGP UPDATE
              Messages.";
        }
        leaf identifier {
          type yang:dotted-quad;
          description
            "BGP Identifier of the router - an unsigned 32-bit,
             non-zero integer that should be unique within an AS.
             The value of the BGP Identifier for a BGP speaker is
             determined upon startup and is the same for every local
             interface and BGP peer.";
          reference
            "RFC 6286: AS-Wide Unique BGP ID for BGP-4. Section 2.1";
        }
        container distance {
          if-feature "ibt:distance";
          description
            "Administrative distances (or preferences) assigned to
             routes received from different sources (external, and
             internal).";
          leaf external {
            type uint8 {
              range "1..255";
            }
            description
              "Administrative distances for routes learned from
               external BGP (eBGP).";
          }
          leaf internal {
            type uint8 {
              range "1..255";
            }
            description
              "Administrative distances for routes learned from
               internal BGP (iBGP).";
          }
        }
        container confederation {
          description
            "Configuration options specifying parameters when the
             local router is within an autonomous system which is
             part of a BGP confederation.";
          reference
            "RFC 5065: Autonomous System Confederations for BGP.";
          leaf identifier {
            type inet:as-number;
            description
              "Confederation identifier for the autonomous system.
               Setting the identifier indicates that the local-AS is
               part of the BGP confederation.";
            reference
              "RFC 5065: Autonomous System Confederations for BGP,
               Section 1.2.";
          }
          leaf-list member-as {
            type inet:as-number;
            description
              "Autonomous system numbers that are to be treated
               as part of the local confederation.";
            reference
              "RFC 5065: Autonomous System Confederations for BGP,
               Section 1.2.";
          }
        }
        container graceful-restart {
          if-feature "ibt:graceful-restart";
          description
            "Parameters relating the graceful restart mechanism for
             BGP.";
          reference
            "RFC 4724: Graceful Restart Mechanism for BGP.";
          uses graceful-restart-config;
        }
        uses global-group-use-multiple-paths;
        uses route-selection-options;
        container afi-safis {
          description
            "List of address-families associated with the BGP
             instance.";
          list afi-safi {
            key "name";
            description
              "AFI,SAFI configuration available for the
               neighbor or group.";
            uses mp-afi-safi-config;
            uses state;
            container graceful-restart {
              if-feature "ibt:graceful-restart";
              description
                "Parameters relating to BGP graceful-restart";
              reference
                "RFC 4724: Graceful Restart Mechanism for BGP.";
              uses mp-afi-safi-graceful-restart-config;
            }
            uses route-selection-options;
            uses add-paths;
            uses global-group-use-multiple-paths;
            uses mp-all-afi-safi-list-contents;
          }
        }
        uses rt-pol:apply-policy-group;
        uses state;
      }

      container neighbors {
        description
          "Configuration and operational state for BGP neighbors.";

        list neighbor {
          key "neighbor-key";
          description
            "List of BGP neighbors configured on the local system,
             uniquely identified by a neighbor key that by default
             corresponds to the remote peer's IP address.";

          leaf neighbor-key {
            type leafref {
              path "../remote-address";
            }
            description
              "The key used to identify this BGP neighbor in the
               list. By default, this references the remote IP
               address of the peer, decoupling the list key from
               the peer address leaf so that implementations can
               more easily augment or deviate the keying strategy
               without disrupting other parts of the model that
               depend on remote-address.";
          }

          leaf remote-address {
            type inet:ip-address;
            mandatory true;
            description
              "The remote IP address of this entry's BGP peer.";
          }

          leaf peer-group {
            type leafref {
              path "../../../peer-groups/peer-group/name";
            }
            description
              "The peer-group with which this neighbor is
               associated.";
          }

          leaf local-address {
            type inet:ip-address;
            config false;
            description
              "The local IP address of this entry's BGP connection.";
          }

          leaf local-port {
            type inet:port-number;
            config false;
            description
              "The local port for the TCP connection between
               the BGP peers.";
          }

          leaf remote-port {
            type inet:port-number;
            config false;
            description
              "The remote port for the TCP connection
               between the BGP peers.  Note that the
               objects local-addr, local-port, remote-addr, and
               remote-port provide the appropriate
               reference to the standard MIB TCP
               connection table.";
          }

          leaf peer-type {
            type ibt:peer-type;
            config false;
            description
              "The type of peering session associated with this
               neighbor.";
            reference
              "RFC 4271: A Border Gateway Protocol 4 (BGP-4),
                         Section 1.1 for iBGP and eBGP.
               RFC 5065: Autonomous System Configuration
                         for Confederation internal and external.";
          }

          leaf identifier {
            type yang:dotted-quad;
            config false;
            description
              "The BGP Identifier of this entry's BGP peer.
               This entry MUST be 0.0.0.0 unless the
               session state is in the OpenConfirm or the
               Established state.";
            reference
              "RFC 4271: A Border Gateway Protocol 4 (BGP-4),
                         Section 4.2, 'BGP Identifier'.";
          }

          leaf dynamically-configured {
            type empty;
            config false;
            description
              "When present, this peer has been created
              dynamically.";
          }

          leaf enabled {
            type boolean;
            default "true";
            description
              "Whether the BGP peer is enabled. In cases where the
               enabled leaf is set to false, the local system should
               not initiate connections to the neighbor, and should
               not respond to TCP connections attempts from the
               neighbor. If the state of the BGP session is
               Established at the time that this leaf is set to
               false, the BGP session should be ceased.

               A transition from 'false' to 'true' will cause
               the BGP Manual Start Event to be generated.
               A transition from 'true' to 'false' will cause
               the BGP Manual Stop Event to be generated.
               This parameter can be used to restart BGP peer
               connections. Care should be used in providing
               write access to this object without adequate
               authentication.";
            reference
              "RFC 4271: A Border Gateway Protocol 4 (BGP-4),
               Section 8.1.2.";
          }

          uses neighbor-group-config;

          container graceful-restart {
            if-feature "ibt:graceful-restart";
            description
              "Parameters relating the graceful restart mechanism for
               BGP.";
            reference
              "RFC 4724: Graceful Restart Mechanism for BGP.";
            uses graceful-restart-config;
            leaf peer-restart-time {
              type uint16 {
                range "0..4096";
              }
              config false;
              description
                "The period of time (advertised by the peer) that the
                 peer expects a restart of a BGP session to take.";
            }

            leaf peer-restarting {
              type boolean;
              config false;
              description
                "This flag indicates whether the remote neighbor is
                 currently in the process of restarting, and hence
                 received routes are currently stale.";
            }

            leaf local-restarting {
              type boolean;
              config false;
              description
                "This flag indicates whether the local session is
                 currently restarting. The flag is cleared after all
                 NLRI have been advertised to the peer, and the
                 End-of-RIB (EOR) marker has been cleared.";
            }

            leaf mode {
              type enumeration {
                enum helper-only {
                  description
                    "The local system is operating in helper-only
                     mode, and hence will not retain forwarding state
                     during a local session restart, but will do so
                     during a restart of the remote peer";
                }
                enum bilateral {
                  description
                    "The local system is operating in both helper
                     mode, and hence retains forwarding state during
                     a remote restart, and also maintains forwarding
                     state during local session restart";
                }
                enum remote-helper {
                  description
                    "The local system is able to retain routes during
                     restart but the remote system is only able to
                     act as a helper";
                }
              }
              config false;
              description
                "This leaf indicates the mode of operation of BGP
                 graceful restart with the peer";
            }
          }

          container prefix-limit {
            description
              "Parameters relating to the prefix limit for the
               AFI-SAFI";

            uses prefix-limit-config-common;

            uses prefix-limit-state-common;
          }

          container afi-safis {
            description
              "Per-address-family configuration parameters associated
               with the neighbor";
            uses bgp-neighbor-afi-safi-list;
          }

          leaf session-state {
            type enumeration {
              enum idle {
                description
                  "Neighbor is down, and in the Idle state of the
                   FSM.";
              }
              enum connect {
                description
                  "Neighbor is down, and the session is waiting for
                   the underlying transport session to be
                   established.";
              }
              enum active {
                description
                  "Neighbor is down, and the local system is awaiting
                   a connection from the remote peer.";
              }
              enum opensent {
                description
                  "Neighbor is in the process of being established.
                   The local system has sent an OPEN message.";
              }
              enum openconfirm {
                description
                  "Neighbor is in the process of being established.
                   The local system is awaiting a NOTIFICATION or
                   KEEPALIVE message.";
              }
              enum established {
                description
                  "Neighbor is up - the BGP session with the peer is
                   established.";
              }
            }
            config false;
            description
              "The BGP peer connection state.";
            reference
              "RFC 4271: A Border Gateway Protocol 4 (BGP-4),
               Section 8.1.2.";
          }
          leaf last-established {
            type yang:date-and-time;
            config false;
            description
              "This timestamp indicates the time that the BGP session
               last transitioned in or out of the Established state.

               The BGP session uptime can be computed by clients as
               the difference between this value and the current time
               (assuming the session is in the Established state,
               per the session-state leaf).";
            reference
              "RFC 4271: A Border Gateway Protocol 4 (BGP-4),
               Section 8.";
          }

          uses bgp-capabilities;
          
          container errors {
            config false;
            description
              "Information about BGP NOTIFICATION messages, sent and
               received for this neighbor.";

            container received {
              description
                "BGP NOTIFICATION message state received from this
                 neighbor.";
              uses bgp-errors-common;
              uses bgp-encapsulated-errors-common;
              uses bgp-errors-common-data;
            }
            container sent {
              description
                "BGP NOTIFICATION message state sent to this
                 neighbor.";
              uses bgp-errors-common;
              uses bgp-encapsulated-errors-common;
              uses bgp-errors-common-data;
            }
          }

          container statistics {
            config false;
            description
              "Statistics per neighbor.";

            leaf established-transitions {
              type yang:zero-based-counter32;
              description
                "Number of transitions to the Established state for
                 the neighbor session. This value is analogous to the
                 bgpPeerFsmEstablishedTransitions object from the
                 standard BGP-4 MIB";
              reference
                "RFC 4273: Definitions of Managed Objects for
                 BGP-4, bgpPeerFsmEstablishedTransitions,
                 RFC 4271: A Border Gateway Protocol 4 (BGP-4),
                 Section 8.";
            }
            container messages {
              description
                "Counters for BGP messages sent to and received from
                 the neighbor";
              container received {
                description
                  "BGP messages counters received from this
                   neighbor.";
                uses bgp-neighbor-messages-common;
              }

              container sent {
                description
                  "BGP messages counters sent to this neighbor.";
                uses bgp-neighbor-messages-common;
              }

              container errors {
                description
                  "BGP errors counted vs. this neighbor.";
                leaf erroneous-updates-withdrawn {
                  type yang:zero-based-counter32;
                  config false;
                  description
                    "The number of BGP UPDATE messages for which the
                     treat-as-withdraw mechanism has been applied
                     based on erroneous message contents.";
                  reference
                    "RFC 7606: Revised Error Handling for BGP UPDATE
                     Messages, Section 2.";
                }
                leaf erroneous-updates-attribute-discarded {
                  type yang:zero-based-counter32;
                  config false;
                  description
                    "The number of BGP UPDATE messages for which the
                     attribute discard mechanism has been applied
                     based on erroneous message contents.";
                  reference
                    "RFC 7606: Revised Error Handling for BGP UPDATE
                     Messages, Section 2.";
                }
              }
            }
            container queues {
              description
                "Counters related to queued messages associated with
                 the BGP neighbor";
              leaf input {
                type yang:gauge32;
                description
                  "The number of messages received from the peer
                   currently queued";
              }
              leaf output {
                type yang:gauge32;
                description
                  "The number of messages queued to be sent to the
                   peer";
              }
            }
            action clear {
              if-feature "ibt:clear-statistics";
              description
                "Clear statistics action command.

                 Execution of this command should result in all the
                 statistics to be cleared and set to 0.";

              input {
                leaf clear-at {
                  type yang:date-and-time;
                  description
                    "Time when the clear action needs to be
                     executed.";
                }
              }
              output {
                leaf clear-finished-at {
                  type yang:date-and-time;
                  description
                    "Time when the clear action command completed.";
                }
              }
            }
          }
        }

        notification established {
          leaf remote-address {
            type leafref {
              path "../../neighbor/remote-address";
            }
            description
              "IP address of the neighbor that went into Established
               state.";
          }
          description
            "The established event is generated
             when the BGP FSM enters the Established state.";
        }

        notification backward-transition {
          leaf remote-addr {
            type leafref {
              path "../../neighbor/remote-address";
            }
            description
              "IP address of the neighbor that changed its state from
               Established state.";
          }
          container notification-received {
            description
              "If the backwards transition was caused by receiving a
               BGP NOTIFICATION message, this is the information
               received in the NOTIFICATION PDU.";

            uses bgp-errors-common;
            uses bgp-encapsulated-errors-common;
          }
          container notification-sent {
            description
              "If the backwards transition was caused by sending a
               BGP NOTIFICATION message, this is the information
               sent in the NOTIFICATION PDU.";

            uses bgp-errors-common;
            uses bgp-encapsulated-errors-common;
          }
          description
            "The backward-transition event is
             generated when the BGP FSM moves out of the
             Established state.";
        }
        action clear {
          if-feature "ibt:clear-neighbors";
          description
            "Clear neighbors action.";

          input {
            choice operation {
              default operation-admin;
              description
                "The type of operation for the clear action.";
              case operation-admin {
                leaf admin {
                  type empty;
                  description
                    "Closes the Established BGP session with a BGP
                     NOTIFICATION message with the Administrative
                     Reset error subcode.";
                  reference
                    "RFC 4486 - Subcodes for BGP Cease Notification
                     Message.";
                }
              }
              case operation-hard {
                leaf hard {
                  type empty;
                  description
                    "Closes the Established BGP session with a BGP
                     NOTIFICATION message with the Hard Reset error
                     subcode.";
                  reference
                    "RFC 8538, Section 3 - Notification Message
                     Support for BGP Graceful Restart.";
                }
              }
              case operation-soft {
                leaf soft {
                  type empty;
                  description
                    "Re-sends the current Adj-Rib-Out to this
                     neighbor.";
                }
              }
              case operation-soft-inbound {
                leaf soft-inbound {
                  if-feature "ibt:route-refresh";
                  type empty;
                  description
                    "Requests the Adj-Rib-In for this neighbor to be
                     re-sent using the BGP Route Refresh feature.";
                }
              }
            }

            leaf clear-at {
              type yang:date-and-time;
              description
                "Time when the clear action command needs to be
                 executed.";
            }
          }
          output {
            leaf clear-finished-at {
              type yang:date-and-time;
              description
                "Time when the clear action command completed.";
            }
          }
        }
      }

      container peer-groups {
        description
          "Configuration for BGP peer-groups";

        list peer-group {
          key "name";
          description
            "List of BGP peer-groups configured on the local system -
             uniquely identified by peer-group name";

          leaf name {
            type string;
            description
              "Name of the BGP peer-group";
          }

          uses neighbor-group-config;
          uses dynamic-peers;

          container graceful-restart {
            if-feature "ibt:graceful-restart";
            description
              "Parameters relating the graceful restart mechanism for
               BGP.";
            reference
              "RFC 4724: Graceful Restart Mechanism for BGP.";
            uses graceful-restart-config;
          }

          container prefix-limit {
            description
              "Parameters relating to the prefix limit for the
               AFI-SAFI";

            uses prefix-limit-config-common;
          }

          container afi-safis {
            description
              "Per-address-family configuration parameters
               associated with the peer-group.";
            list afi-safi {
              key "name";
              description
                "AFI, SAFI configuration available for the
                 neighbor or group";
              reference
                "RFC 4724: Graceful Restart Mechanism for BGP.";
              uses mp-afi-safi-config;
              container graceful-restart {
                if-feature "ibt:graceful-restart";
                description
                  "Parameters relating to BGP graceful-restart";
                uses mp-afi-safi-graceful-restart-config;
              }
              uses add-paths;
              uses bgp-neighbor-use-multiple-paths;
              uses mp-all-afi-safi-list-contents;
            }
          }
        }
      }

      uses rib;
    }
  }
}
