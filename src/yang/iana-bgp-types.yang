module iana-bgp-types {
  yang-version 1.1;
  namespace "urn:ietf:params:xml:ns:yang:iana-bgp-types";
  prefix bt;

  import ietf-inet-types {
    prefix inet;
    reference
      "RFC 9911: Common YANG Types.";
  }
  import ietf-yang-types {
    prefix yang;
    reference
      "RFC 9911: Common YANG Types.";
  }
  import ietf-yang-semver {
    prefix ysv;
    reference
      "I-D.ietf-netmod-yang-semver: YANG Semantic Versioning";
  }

  organization
    "IANA";
  contact
    "Internet Assigned Numbers Authority

     Postal: ICANN
             12025 Waterfront Drive, Suite 300
             Los Angeles, CA 90094-2536
             United States of America
     Tel:    +1 310 301 5800
     <mailto:iana@iana.org>

     Authors: Mahesh Jethanandani (mjethanandani at gmail.com),
              Keyur Patel (keyur at arrcus.com),
              Susan Hares (shares at ndzh.com),
              Jeffrey Haas (jeffrey.haas at hpe.com).";

  description
    "This module contains general data definitions for use in BGP.
     It can be imported by modules that make use of BGP attributes.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    ysv:version 0.0.9;
    reference
      "RFC XXXX: YANG module for Border Gateway Protocol (BGP-4).";
  }

  /*
   * Features.
   */

  feature add-paths {
    description
      "Advertisement of multiple paths for the same address prefix
       without the new paths implicitly replacing any previous
       ones.";
    reference
      "RFC 7911: Advertisement of Multiple Paths in BGP.";
  }

  feature bfd {
    description
      "Support for BFD detection of BGP neighbor reachability.";
    reference
      "RFC 5880: Bidirectional Forward Detection (BFD),
       RFC 5881: Bidirectional Forward Detection for IPv4 and IPv6
                 (Single Hop),
       RFC 5883: Bidirectional Forwarding Detection (BFD) for
                 Multihop Paths.";
  }

  feature clear-neighbors {
    description
      "Clearing of BGP neighbors is supported.";
  }

  feature clear-routes {
    description
      "Clearing of BGP routes is supported.";
  }

  feature clear-statistics {
    description
      "Clearing of BGP statistics is supported.";
  }

  feature damping {
    description
      "Weighted route dampening is supported.";
  }

  feature distance {
    description
      "BGP distance for implementations that expose routing table
       preferences for route selection for internal and external
       BGP.";
  }

  feature graceful-restart {
    description
      "Graceful restart as defined in RFC 4724 is supported.";
  }

  feature route-refresh {
    description
      "Support for the BGP Route Refresh capability.";
    reference
      "RFC 2918: Route Refresh Capability for BGP-4.";
  }

  feature ttl-security {
    description
      "BGP Time To Live (TTL) security check support.";
    reference
      "RFC 5082: The Generalized TTL Security Mechanism (GTSM).";
  }

  /*
   * Identities.
   */

  /* BGP Origin Attribute Types. */

  typedef bgp-origin-attr-type {
    type enumeration {
      enum igp {
        description
          "Origin of the NLRI is internal";
      }
      enum egp {
        description
          "Origin of the NLRI is EGP";
      }
      enum incomplete {
        description
          "Origin of the NLRI is neither IGP or EGP";
      }
    }
    description
      "Type definition for standard BGP origin attribute";
    reference
      "RFC 4271: A Border Gateway Protocol 4 (BGP-4), Sec 4.3.";
  }

  /* BGP AS_PATH Segment Type Identities. */

  typedef as-path-segment-type {
    type enumeration {
      enum as-set {
        value 1;
        description
          "Unordered set of autonomous systems that a route in the
           UPDATE message has traversed.";
        reference
          "RFC 4271: A Border Gateway Protocol 4 (BGP-4),
           Section 4.3."; }

      enum as-sequence {
        value 2;
        description
          "Ordered set of autonomous systems that a route in the
           UPDATE message has traversed.";
        reference
          "RFC 4271: A Border Gateway Protocol 4 (BGP-4),
           Section 4.3.";
      }

      enum as-confed-sequence {
        value 3;
        description
          "Ordered set of Member Autonomous Systems in the local
           confederation that the UPDATE message has traversed.";
        reference
          "RFC 5065: Autonomous System Configuration for BGP.";
      }

      enum as-confed-set {
        value 4;
        description
          "Unordered set of Member Autonomous Systems in the local
           confederation that the UPDATE message has traversed.";
        reference
          "RFC 5065: Autonomous System Configuration for BGP.";
      }
    }
    description
      "BGP AS_PATH segment types.";
  }

  /* BGP Peer-Types */

  typedef peer-type {
    type enumeration {
      enum internal {
        description
          "Internal (IBGP) peer";
      }
      enum external {
        description
          "External (EBGP) peer";
      }
      enum confederation-internal {
        description
          "Confederation Internal (IBGP) peer.";
      }
      enum confederation-external {
        description
          "Confederation External (EBGP) peer.";
      }
    }
    description
      "Labels a peer or peer group as explicitly internal,
       external, or the related confederation type.";
    reference
      "RFC 4271: A Border Gateway Protocol 4 (BGP-4), Sec 1.1.
       RFC 5065: Autonomous System Configuration for BGP.";
  }

  /* BGP Capability Identities. */

  identity bgp-capability {
    description
      "Base identity for a BGP capability";
  }

  identity mp-bgp {
    base bgp-capability;
    description
      "Multi-protocol extensions to BGP.";
    reference
      "RFC 4760: Multiprotocol Extentions for BGP-4.";
  }

  identity route-refresh {
    base bgp-capability;
    description
      "The BGP route-refresh functionality";
    reference
      "RFC 2918: Route Refresh Capability for BGP-4.";
  }

  identity asn32 {
    base bgp-capability;
    description
      "4-byte (32-bit) AS number functionality";
    reference
      "RFC6793: BGP Support for Four-Octet Autonomous System (AS)
                Number Space.";
  }

  identity graceful-restart {
    if-feature "graceful-restart";
    base bgp-capability;
    description
      "Graceful restart functionality";
    reference
      "RFC 4724: Graceful Restart Mechanism for BGP.";
  }

  identity add-paths {
    if-feature "add-paths";
    base bgp-capability;
    description
      "Advertisement of multiple paths for the same address prefix
       without the new paths implicitly replacing any previous
       ones.";
    reference
      "RFC 7911: Advertisement of Multiple Paths in BGP.";
  }

  /* BGP AFI-SAFI Type Identities. */

  identity afi-safi-type {
    description
      "Base identity type for AFI,SAFI tuples for BGP-4";
    reference
      "RFC4760: Multiprotocol Extentions for BGP-4.";
  }

  identity ipv4-unicast {
    base afi-safi-type;
    description
      "IPv4 unicast (AFI,SAFI = 1,1)";
    reference
      "RFC4760: Multiprotocol Extentions for BGP-4.";
  }

  identity ipv4-labeled-unicast {
    base afi-safi-type;
    description
      "Labeled IPv4 unicast (AFI,SAFI = 1,4)";
    reference
      "RFC 8277: Using BGP to Bind MPLS Labels to Address Prefixes.";
  }

  identity ipv6-unicast {
    base afi-safi-type;
    description
      "IPv6 unicast (AFI,SAFI = 2,1)";
    reference
      "RFC4760: Multiprotocol Extentions for BGP-4.";
  }

  identity ipv6-labeled-unicast {
    base afi-safi-type;
    description
      "Labeled IPv6 unicast (AFI,SAFI = 2,4)";
    reference
      "RFC 8277: Using BGP to Bind MPLS Labels to Address Prefixes.";
  }

  identity l3vpn-ipv4-unicast {
    base afi-safi-type;
    description
      "Unicast IPv4 MPLS L3VPN (AFI,SAFI = 1,128)";
    reference
      "RFC 4364: BGP/MPLS IP Virtual Private Networks (VPNs).";
  }

  identity l3vpn-ipv4-multicast {
    base afi-safi-type;
    description
      "Multicast IPv4 MPLS L3VPN (AFI,SAFI = 1,129)";
    reference
      "RFC 6514: BGP Encodings and Procedures for Multicast in
       MPLS/BGP IP VPNs.";
  }

  identity l3vpn-ipv6-unicast {
    base afi-safi-type;
    description
      "Unicast IPv6 MPLS L3VPN (AFI,SAFI = 2,128)";
    reference
      "RFC 4659: BGP-MPLS IP Virtual Private Network (VPN) Extension
       for IPv6 VPN.";
  }

  identity l3vpn-ipv6-multicast {
    base afi-safi-type;
    description
      "Multicast IPv6 MPLS L3VPN (AFI,SAFI = 2,129)";
    reference
      "RFC 6514: BGP Encodings and Procedures for Multicast in
       MPLS/BGP IP VPNs.";
  }

  identity l2vpn-evpn {
    base afi-safi-type;
    description
      "BGP MPLS Based Ethernet VPN (AFI,SAFI = 25,70)";
    reference
      "RFC 7432: BGP MPLS-Based Ethernet VPN.";
  }

  identity l2vpn-vpls {
    base afi-safi-type;
    description
      "BGP-signalled VPLS (AFI,SAFI = 25,65)";
    reference
      "RFC 4761: Virtual Private LAN Service (VPLS) Using BGP for
       Auto-Discovery and Signaling.";
  }

  /* BGP Remove Private AS Identities. */

  identity remove-private-as-option {
    description
      "Base identity for options for removing private autonomous
       system numbers from the AS_PATH attribute";
  }

  identity private-as-remove-all {
    base remove-private-as-option;
    description
      "Strip all private autonomous system numbers from the AS_PATH.
       This action is performed regardless of the other content of
       the AS_PATH attribute, and for all instances of private AS
       numbers within that attribute.";
  }

  identity private-as-replace-all {
    base remove-private-as-option;
    description
      "Replace all instances of private autonomous system numbers in
       the AS_PATH with the local BGP speaker's autonomous system
       number. This action is performed regardless of the other
       content of the AS_PATH attribute, and for all instances of
       private AS number within that attribute.";
  }

  /*
   * Typedefs.
   */

  typedef bgp-session-direction {
    type enumeration {
      enum inbound {
        description
          "Refers to all NLRI received from the BGP peer";
      }
      enum oubound {
        description
          "Refers to all NLRI advertised to the BGP peer";
      }
    }
    description
      "Type to describe the direction of NLRI transmission";
  }

  /* BGP Route Reflector Types. */

  typedef rr-cluster-id-type {
    type union {
      type uint32;
      type yang:dotted-quad;
    }
    description
      "Union type for route reflector cluster ids:
       option 1: 4-byte number
       option 2: IP address";
    reference
      "RFC 4456: BGP Route Reflection.";
  }

  /* BGP Graceful Restart Types. */

  typedef graceful-restart-time-type {
    type uint16 {
      range "0..4096";
    }
    units "seconds";
    description
      "This is the estimated time (in seconds) it will take for the
       BGP session to be re-established after a restart.  This can be
       used to speed up routing convergence by its peer in case that
       the BGP speaker does not come back after a restart.";
    reference
       "RFC 4724: Graceful Restart Mechanism for BGP, Section 3.";
  }

  typedef graceful-restart-flags {
    type bits {
      bit restart {
        position 0;
        description
          "The most significant bit is defined as the Restart
           State (R) bit, which can be used to avoid possible
           deadlock caused by waiting for the End-of-RIB marker
           when multiple BGP speakers peering with each other
           restart.  When set (value 1), this bit indicates
           that the BGP speaker has restarted, and its peer
           MUST NOT wait for the End-of-RIB marker from the
           speaker before advertising routing information to
           the speaker.";
        reference
          "RFC 4724: Graceful Restart Mechanism for BGP,
           Section 3.";
      }
      bit notification {
        position 1;
        description
          "The second most significant bit is defined in [RFC 8538]
           as the Graceful Notification ('N') bit.  It is used to
           indicate Graceful Restart support for BGP NOTIFICATION
           messages.  A BGP speaker indicates support for the
           procedures in this document by advertising a Graceful
           Restart Capability with its 'N' bit set (value 1).";
        reference
          "RFC 8538: Notification Message Support for BGP Graceful
           Restart, Section 2.";
      }
    }
    description
      "Restart Flags bits as defined for BGP Graceful Restart and its
       extensions.";
    reference
      "RFC 4724: Graceful Restart Mechanism for BGP,
       RFC 8538: Notification Message Support for BGP Graceful
       Restart.";
  }

  typedef graceful-restart-flags-for-afi {
    type bits {
      bit forwarding-preserved {
        position 0;
        description
          "The most significant bit is defined as the
           Forwarding State (F) bit, which can be used to
           indicate whether the forwarding state for routes
           that were advertised with the given AFI and SAFI
           has indeed been preserved during the previous BGP
           restart.  When set (value 1), the bit indicates
           that the forwarding state has been preserved.";
         reference
           "RFC 4724: Graceful Restart Mechanism for BGP,
            Section 3.";
      }
    }
    description
      "Flags for Address Family bits as defined for BGP Graceful
       Restart and its extensions.";
    reference
      "RFC 4724: Graceful Restart Mechanism for BGP.";
  }

  /* BGP Remove Private AS Types. */

  typedef remove-private-as-option {
    type identityref {
      base remove-private-as-option;
    }
    description
      "Set of options for configuring how private AS path numbers
       are removed from advertisements";
  }

}
