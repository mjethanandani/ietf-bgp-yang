module ietf-bgp-rib-types {
  yang-version "1.1";
  namespace "urn:ietf:params:xml:ns:yang:ietf-bgp-rib-types";
  prefix "brt";

  organization
    "IETF IDR Working Group";

  contact
    "WG Web:   <http://tools.ietf.org/wg/idr>
     WG List:  <idr@ietf.org>

     Editor:  Mahesh Jethanandani (mjethanandani@gmail.com)
     Authors: Keyur Patel,
              Mahesh Jethanandani,
              Susan Hares";

  description
    "Defines identity and type defintions associated with
     the BGP RIB modules";

  revision "YYYY-MM-DD" {
    description
      "Initial Version";
    reference 
      "RFC XXX, BGP Model for Service Provider Network.";
  }

  identity invalid-route-reason {
    description
      "Base identity for reason code for routes that are rejected as
       invalid.  Some derived entities are based on BMP v3";
    reference
      "BGP Monitoring Protocol (draft-ietf-grow-bmp-07)";
  }

  identity invalid-cluster-loop {
    base invalid-route-reason;
    description
      "Route was invalid due to CLUSTER_LIST loop";
  }

  identity invalid-as-loop {
    base invalid-route-reason;
    description
      "Route was invalid due to AS_PATH loop";
  }

  identity invalid-originator {
    base invalid-route-reason;
    description
      "Route was invalid due to ORIGINATOR_ID, e.g., update has
      local router as originator";
  }

  identity invalid-confed {
    base invalid-route-reason;
    description
      "Route was invalid due to a loop in the AS_CONFED_SEQUENCE or
       AS_CONFED_SET attributes";
  }

  identity bgp-not-selected-bestpath {
    description
      "Base identity for indicating reason a route was was not
       selected by BGP route selection algorithm";
    reference
      "RFC 4271 - Section 9.1";
  }

  identity local-pref-lower {
    base bgp-not-selected-bestpath;
    description
      "Route has a lower localpref attribute than current best path";
    reference
      "RFC 4271 - Section 9.1.2";
  }

  identity as-path-longer {
    base bgp-not-selected-bestpath;
    description
      "Route has a longer AS path attribute than current best path";
    reference
      "RFC 4271 - Section 9.1.2.2 (a)";
  }

  identity origin-type-higher {
    base bgp-not-selected-bestpath;
    description
      "Route has a higher origin type, i.e., IGP origin is preferred
      over EGP or incomplete";
    reference
      "RFC 4271 - Section 9.1.2.2 (b)";
  }

  identity med-higher {
    base bgp-not-selected-bestpath;
    description
      "Route has a higher MED, or metric, attribute than the current
       best path";
    reference
      "RFC 4271 - Section 9.1.2.2 (c)";
  }

  identity prefer-external {
    base bgp-not-selected-bestpath;
    description
      "Route source is via IGP, rather than EGP.";
    reference
      "RFC 4271 - Section 9.1.2.2 (d)";
  }

  identity nexthop-cost-higher {
    base bgp-not-selected-bestpath;
    description
      "Route has a higher interior cost to the next hop.";
    reference
      "RFC 4271 - Section 9.1.2.2 (e)";
  }

  identity higher-router-id {
    base bgp-not-selected-bestpath;
    description
      "Route was sent by a peer with a higher BGP Identifier value,
      or router id";
    reference
      "RFC 4271 - Section 9.1.2.2 (f)";
  }

  identity higher-peer-address {
    base bgp-not-selected-bestpath;
    description
      "Route was sent by a peer with a higher IP address";
    reference
      "RFC 4271 - Section 9.1.2.2 (g)";
  }

  identity bgp-not-selected-policy {
    description
      "Base identity for reason code for routes that are rejected
       due to policy";
  }

  identity rejected-import-policy {
    base bgp-not-selected-policy;
    description
      "Route was rejected after apply import policies";
  }

  identity tunnel-encapsulation-type {
    description
      "Types of tunnel encapsulation, as described by the Tunnel
       Encapsulation attribute";
    reference
      "RFC5512";
    }

  identity srte-policy-tunnel {
    base tunnel-encapsulation-type;
    description
      "Segment Routing Traffic Engineering Policy tunnel.";
    reference
      "draft-previdi-idr-segment-routing-te-policy";
  }

  identity tunnel-encapsulation-subtlv-type {
    description
      "SubTLVs of the Tunnel Encapsulation attribute";
    reference
      "RFC5512";
  }

  identity tunnel-remote-endpoint {
    base tunnel-encapsulation-subtlv-type;
    description
      "Remote endpoint of the tunnel.";
    reference
      "RFC5512";
  }

  identity tunnel-color {
    base tunnel-encapsulation-subtlv-type;
    description
      "Colour of the tunnel";
    reference
      "RFC5512";
  }

  identity srte-preference {
    base tunnel-encapsulation-subtlv-type;
    description
      "Preference of the SR-TE policy entry described by
       the tunnel encapsulation attribute.";
    reference
      "draft-previdi-idr-segment-routing-te-policy";
  }

  identity srte-binding-sid {
    base tunnel-encapsulation-subtlv-type;
    description
      "Binding SID to be used by the SR-TE policy described
       by the tunnel encapsulation attribute.";
    reference
      "draft-previdi-idr-segment-routing-te-policy";
  }

  identity srte-segment-list {
    base tunnel-encapsulation-subtlv-type;
    description
      "Segment lists to be used by the SR-TE policy described
       by the tunnel encapsulation attribute.";
    reference
      "draft-previdi-idr-segment-routing-te-policy";
  }

  identity srte-segment-list-subtlv {
    description
      "SubTLVs of the SR-TE Policy Segment List sub-TLV of the
       Tunnel Encapsulation attribute.";
    reference
      "draft-previdi-idr-segment-routing-te-policy";
  }

  identity srte-segment-list-weight {
    base srte-segment-list-subtlv;
    description
      "Weight of the segment list within the SR-TE policy";
    reference
      "draft-previdi-idr-segment-routing-te-policy";
  }

  identity srte-segment-list-segment {
    base srte-segment-list-subtlv;
    description
      "An individual element within the SR-TE Policy Segment
       List.";
  }
}
