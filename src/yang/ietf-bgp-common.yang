submodule ietf-bgp-common {
  yang-version 1.1;
  belongs-to ietf-bgp {
    prefix bgp;
  }

  import ietf-bgp-types {
    prefix ibt;
    reference
      "RFC XXXX: YANG Model for Border Gateway Protocol (BGP-4).";
  }
  import ietf-bgp-community-types {
    prefix ibct;
    reference
      "RFC XXXX: YANG Model for Border Gateway Protocol (BGP-4).";
  }
  import ietf-bgp-session-security {
    prefix ibss;
    reference
      "RFC XXXX: YANG Model for Border Gateway Protocol (BGP-4).";
  }
  import ietf-interfaces {
    prefix if;
    reference
      "RFC 8343: A YANG Data Model for Interface Management.";
  }
  import ietf-inet-types {
    prefix inet;
    reference
      "RFC 9911: Common YANG Data Types.";
  }
  import ietf-routing-policy {
    prefix rt-pol;
    reference
      "RFC 9067: A YANG Data Model for Routing Policy.";
  }
  import ietf-yang-types {
    prefix yang;
    reference
      "RFC 9911: Common YANG Data Types.";
  }
  import ietf-bfd-types {
    prefix bfd-types;
    reference
      "RFC 9314: YANG Data Model for Bidirectional Forward
       Detection.";
  }
  import ietf-tcp {
    prefix tcp;
    reference
      "RFC 9648: YANG Data Model for TCP.";
  }
  import ietf-yang-semver {
    prefix ysv;
    reference
      "I-D.ietf-netmod-yang-semver: YANG Semantic Versioning";
  }
  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This sub-module contains common groupings that are common across
     multiple contexts within the BGP module. That is to say that
     they may be application to a subset of global, peer-group, or
     neighbor contexts.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    ysv:version 0.0.9;
    reference
      "RFC XXXX: YANG Model for Border Gateway Protocol (BGP-4).";
  }

  grouping neighbor-group-timers {
    description
      "Configuration parameters related to timers associated with
       the BGP peer.";
    leaf connect-retry-interval {
      type uint16 {
        range "1..max";
      }
      units "seconds";
      default "120";
      description
        "Time interval (in seconds) for the ConnectRetryTimer. The
         suggested value for this timer is 120 seconds.";
      reference
        "RFC 4271: A Border Gateway Protocol 4 (BGP-4),
         Section 8.2.2.";
    }
    leaf hold-time {
      type uint16 {
        range "0 | 3..65535";
      }
      units "seconds";
      description
        "Time interval (in seconds) for the HoldTimer established
         with the peer.  When read as operational data (ro), the
         value of this object is calculated by this BGP speaker,
         using the smaller of the values in hold-time that was
         configured (rw) in the running datastore and the Hold Time
         received in the OPEN message.

         The suggested value for this timer is 90 seconds.

         This value must be at least three seconds
         if it is not zero (0).

         If the Hold Timer has not been established
         with the peer this object MUST have a value
         of zero (0).

         If the configured value of hold-time object was
         a value of (0), then when read this object MUST have a
         value of (0) also.";
      reference
        "RFC 4271: A Border Gateway Protocol 4 (BGP-4), Section 4.2,
         RFC 4271: A Border Gateway Protocol 4 (BGP-4), Section 10.";
    }
    leaf keepalive {
      type uint16 {
        range "0..21845";
      }
      units "seconds";
      description
        "When used as a configuration (rw) value, this Time interval
         (in seconds) for the KeepAlive timer configured for this BGP
         speaker with this peer.  A reasonable maximum value for this
         timer would be one-third of the configured hold-time.

         In the absence of explicit configuration of the keepalive
         value, operationally it SHOULD have a value of one-third of
         the negotiated hold-time.

         If the value of this object is zero (0), no periodic
         KEEPALIVE messages are sent to the peer after the BGP
         connection has been established.

         The actual time interval for the KEEPALIVE messages is
         indicated by operational value of keepalive.";
      reference
        "RFC 4271: A Border Gateway Protocol 4 (BGP-4), Section 4.4,
         RFC 4271: A Border Gateway Protocol 4 (BGP-4), Section 10.";
    }
    leaf min-as-origination-interval {
      type uint16 {
        range "0..max";
      }
      units "seconds";
      description
        "Time interval (in seconds) for the MinASOriginationInterval
         timer. The suggested value for this timer is 15 seconds.";
      reference
        "RFC 4271: A Border Gateway Protocol 4 (BGP-4), Section
         9.2.1.2,
         RFC 4271: A Border Gateway Protocol 4 (BGP-4), Section 10.";
    }
    leaf min-route-advertisement-interval {
      type uint16 {
        range "0..max";
      }
      units "seconds";
      description
        "Time interval (in seconds) for the
         MinRouteAdvertisementInterval timer.
         The suggested value for this timer is 30
         seconds for EBGP connections and 5
         seconds for IBGP connections.";
      reference
        "RFC 4271: A Border Gateway Protocol 4 (BGP-4), Section
         9.2.1.1,
         RFC 4271: A Border Gateway Protocol 4 (BGP-4), Section 10.";
    }
  }

  grouping bgp-neighbor-use-multiple-paths {
    description
      "Multi-path configuration and state applicable to a BGP
       neighbor";
    container use-multiple-paths {
      description
        "Parameters related to the use of multiple-paths for the same
         NLRI when they are received only from this neighbor";
      leaf enabled {
        type boolean;
        default "false";
        description
          "Whether the use of multiple paths for the same NLRI is
           enabled for the neighbor.";
      }
      container ebgp {
        description
          "Multi-path configuration for eBGP.";
        leaf allow-multiple-as {
          type boolean;
          default "false";
          description
            "Allow multi-path to use paths from different neighboring
             ASes. The default is to only consider multiple paths
             from the same neighboring AS.";
        }
      }
    }
  }

  grouping neighbor-group-config {
    description
      "Neighbor level configuration items.";
    leaf peer-as {
      type inet:as-number;
      description
        "AS number of the peer.";
    }
    leaf local-as {
      type inet:as-number;
      description
        "The local autonomous system number that is to be used when
         establishing sessions with the remote peer or peer group, if
         this differs from the global BGP router autonomous system
         number.";
      reference
        "RFC 7705: Autonomous System Migration Mechanisms and Their
         Effects on the BGP AS_PATH Attribute.";
    }
    leaf treat-as-withdraw {
      type boolean;
      description
        "Specify whether erroneous UPDATE messages for which the NLRI
         can be extracted are treated as though the NLRI is withdrawn
         - avoiding session reset.  The suggested implementation
         default is true.";
      reference
        "RFC 7606: Revised Error Handling for BGP UPDATE Messages.";
    }
    leaf enforce-first-as {
       type boolean;
       description
         "When set to true, the leftmost AS in the AS_PATH of BGP
          UPDATE messages received from external peers MUST be equal
          to autonomous system number of the peer that sent the
          message.

          If the check determines they are not equal and
          treat-as-withdraw is false, a BGP NOTIFICATION is sent.  If
          treat-as-withdraw is true, the routes will be withdraw
          without and no NOTIFICATION is sent.";
       reference
         "RFC 4271: A Border Gateway Protocol 4 (BGP-4),
          Section 6.3.
          RFC 7606: Revised Error Handling for BGP UPDATE Messages.";
    }
    leaf remove-private-as {
      type ibt:remove-private-as-option;
      description
        "When this leaf is specified, remove private AS numbers from
         updates sent to peers.";
      reference
        "RFC 6996: Autonomous System (AS) Reservation for Private
         Use.";
    }
    container route-flap-damping {
      if-feature "ibt:damping";
      leaf enable {
        type boolean;
        default "false";
        description
          "Enable route flap damping.";
      }
      leaf suppress-above {
        type decimal64 {
          fraction-digits 1;
        }
        default "3.0";
        description
          "This is the value of the instability metric at which
           route suppression takes place. A route is not installed
           in the forwarding information base (FIB), or announced
           even if it is reachable during the period that it is
           suppressed.";
      }
      leaf reuse-above {
        type decimal64 {
          fraction-digits 1;
        }
        default "2.0";
        description
          "This is the value of the instability metric at which a
           suppressed route becomes unsuppressed if it is reachable
           but currently suppressed. The value assigned to
           reuse-below must be less than suppress-above.";
      }
      leaf max-flap {
        type decimal64 {
          fraction-digits 1;
        }
        default "16.0";
        description
          "This is the upper limit of the instability metric. This
           value must be greater than the larger of 1 and
           suppress-above.";
      }
      leaf reach-decay {
        type uint32;
        units "seconds";
        default "300";
        description
          "This value specifies the time desired for the instability
           metric value to reach one-half of its current value when
           the route is reachable. This half-life value determines
           the rate at which the metric value is decayed. A smaller
           half-life value makes a suppressed route reusable sooner
           than a larger value.";
      }
      leaf unreach-decay {
        type uint32;
        units "seconds";
        default "900";
        description
          "This value acts the same as reach-decay except that it
           specifies the rate at which the instability metric is
           decayed when a route is unreachable. It should have a
           value greater than or equal to reach-decay.";
      }
      leaf keep-history {
        type uint32;
        units "seconds";
        default "1800";
        description
          "This value specifies the period over which the route
           flapping history is to be maintained for a given route.
           The size of the configuration arrays described below is
           directly affected by this value.";
      }
      description
        "Routes learned via BGP are subject to weighted route
         damping.";
      reference
        "RFC 2439: BGP Route Flap Damping.";
    }
    leaf-list send-community {
      if-feature "ibct:send-communities";
      type identityref {
        base "ibct:send-community-feature";
      }
      description
        "When supported, this tells the router to propagate any
         communities that are attached to BGP routes for these
         community-types.";
    }
    leaf description {
      type string;
      description
        "An optional textual description (intended primarily for use
         with a peer or group";
    }

    container timers {
      description
        "Timers related to a BGP neighbor";
      uses neighbor-group-timers;
    }

    container transport {
      description
        "Transport session parameters for the BGP neighbor";
      uses neighbor-group-transport-config;
    }

    container logging-options {
      description
        "Logging options for events related to the BGP neighbor or
         group";
      leaf log-neighbor-state-changes {
        type boolean;
        default "true";
        description
          "Configure logging of peer state changes.  Default is to
           enable logging of peer state changes.

           Note: Documenting demotion from Established state is
                 desirable, but documenting all backward transitions
                 is problematic, and should be avoided.";
      }
    }

    uses neighbor-group-route-reflector;
    uses neighbor-group-as-path-options;

    leaf advertise-inactive-routes {
      type boolean;
      default "false";
      description
        "Advertise inactive routes to external peers.  The default
         is to only advertise active routes.";
      reference
        "I-D.ietf-idr-best-external: Advertisement of the best
         external route in BGP.";
    }

    uses add-paths;
    uses bgp-neighbor-use-multiple-paths;
    uses rt-pol:apply-policy-group;
  }

  grouping neighbor-group-transport-config {
    description
      "Configuration parameters relating to the transport protocol
       used by the BGP session to the peer.";

    leaf local-address {
      type union {
        type inet:ip-address;
        type if:interface-ref;
      }
      description
        "Set the local IP (either IPv4 or IPv6) address to use for
         the session when sending BGP update messages. This may be
         expressed as either an IP address or reference to the name
         of an interface.";
    }

    leaf tcp-mss {
      type tcp:mss;
      description
        "Maximum Segment Size (MSS) desired on this connection.
         Note, the 'effective send MSS' can be smaller than
         what is configured here.";
       reference
         "RFC 9293: Transmission Control Protocol (TCP)
                    Specification.";
    }

    leaf mtu-discovery {
      type boolean;
      default "true";
      description
        "Turns path mtu discovery for BGP TCP sessions on (true) or
         off (false).";
      reference
        "RFC 1191: Path MTU discovery.";
    }

    container ebgp-multihop {
      description
        "eBGP multi-hop parameters for the BGP peer-group";
      leaf enabled {
        type boolean;
        default "false";
        description
          "When enabled, the referenced group or neighbors are
           permitted to be indirectly connected - including cases
           where the TTL can be decremented between the BGP peers";
      }
      leaf multihop-ttl {
        type uint8;
        description
          "Time-to-live value to use when packets are sent to the
           referenced group or neighbors and ebgp-multihop is
           enabled";
      }
    }

    leaf passive-mode {
      type boolean;
      default "false";
      description
        "Wait for peers to issue requests to open a BGP session,
         rather than initiating sessions from the local router.";
    }

    leaf ttl-security {
      if-feature "ibt:ttl-security";
      type uint8;
      default "255";
      description
        "BGP Time To Live (TTL) security check.";
      reference
        "RFC 5082: The Generalized TTL Security Mechanism (GTSM),
         RFC 7454: BGP Operations and Security.";
    }

    uses "ibss:bgp-session-security";

    container bfd {
      if-feature "ibt:bfd";
      uses bfd-types:client-cfg-parms;
      description
        "BFD client configuration.";
      reference
        "RFC 9314: YANG Data Model for Bidirectional Forwarding
         Detection.";
    }
  }

  grouping graceful-restart-config {
    description
      "Configuration parameters relating to BGP graceful restart.";
    leaf enabled {
      type boolean;
      default "false";
      description
        "Enable or disable the graceful-restart capability.";
    }
    leaf restart-time {
      type ibt:graceful-restart-time-type;
      description
        "Estimated time (in seconds) for the local BGP speaker to
         restart a session. This value is advertise in the graceful
         restart BGP capability.  This is a 12-bit value, referred to
         as Restart Time in RFC4724.  Per RFC4724, the suggested
         default value is <= the hold-time value.";
      reference
        "RFC 4724: Graceful Restart Mechanism for BGP.";
    }
    leaf stale-routes-time {
      type uint32;
      description
        "An upper-bound on the time that stale routes will be
         retained by a router after a session is restarted. If an
         End-of-RIB (EOR) marker is received prior to this timer
         expiring, stale-routes will be flushed upon its receipt - if
         no EOR is received, then when this timer expires stale paths
         will be purged. This timer is referred to as the
         Selection_Deferral_Timer in RFC4724";
      reference
        "RFC 4724: Graceful Restart Mechanism for BGP.";
    }
    leaf helper-only {
      type boolean;
      default "true";
      description
        "Enable graceful-restart in helper mode only. When this leaf
         is set, the local system does not retain forwarding its own
         state during a restart, but supports procedures for the
         receiving speaker, as defined in RFC4724.";
      reference
        "RFC 4724: Graceful Restart Mechanism for BGP.";
    }
  }

  grouping global-group-use-multiple-paths {
    description
      "Common grouping used for both global and groups which provides
       configuration and state parameters relating to use of multiple
       paths";
    container use-multiple-paths {
      description
        "Parameters related to the use of multiple paths for the
         same NLRI";
      leaf enabled {
        type boolean;
        default "false";
        description
          "Whether the use of multiple paths for the same NLRI is
           enabled for the neighbor. This value is overridden by any
           more specific configuration value.";
      }
      container ebgp {
        description
          "Multi-Path parameters for eBGP.";
        leaf allow-multiple-as {
          type boolean;
          default "false";
          description
            "Allow multi-path to use paths from different neighboring
             ASes.  The default is to only consider multiple paths
             from the same neighboring AS.";
        }
        leaf maximum-paths {
          type uint32;
          default "1";
          description
            "Maximum number of parallel paths to consider when using
             BGP multi-path. The default is use a single path.";
        }
      }
      container ibgp {
        description
          "Multi-Path parameters for iBGP.";
        leaf maximum-paths {
          type uint32;
          default "1";
          description
            "Maximum number of parallel paths to consider when using
             iBGP multi-path. The default is to use a single path";
        }
      }
    }
  }

  grouping route-selection-options {
    description
      "Configuration and state relating to route selection options";
    container route-selection-options {
      description
        "Parameters relating to options for route selection";
      leaf always-compare-med {
        type boolean;
        default "false";
        description
          "Compare multi-exit discriminator (MED) value from
           different ASes when selecting the best route.  The default
           behavior is to only compare MEDs for paths received from
           the same AS.";
      }
      leaf ignore-as-path-length {
        type boolean;
        default "false";
        description
          "Ignore the AS path length when selecting the best path.
           The default is to use the AS path length and prefer paths
           with a shorter length.";
      }
      leaf external-compare-router-id {
        type boolean;
        default "true";
        description
          "When comparing similar routes received from external BGP
           peers, use the router-id as a criterion to select the
           active path.";
      }
      leaf enable-aigp {
        type boolean;
        default "false";
        description
          "Flag to enable sending / receiving accumulated IGP
           attribute in routing updates";
        reference
          "RFC 7311: AIGP Metric Attribute for BGP.";
      }
      leaf ignore-next-hop-igp-metric {
        type boolean;
        default "false";
        description
          "Ignore the IGP metric to the next-hop when calculating BGP
           best-path. The default is to select the route for which
           the metric to the next-hop is lowest";
      }
      leaf enable-med {
        type boolean;
        default "false";
        description
          "Flag to enable sending/receiving of MED metric attribute
           in routing updates.";
      }
      container med-plus-igp {
        leaf enabled {
          type boolean;
          default "false";
          description
            "When enabled allows BGP to use MED and IGP values
             defined below to determine the optimal route.";
          reference
            "RFC 4451: BGP MED Considerations.";
        }
        leaf igp-multiplier {
          type uint16;
          default 1;
          description
            "Specifies an IGP cost multiplier.";
          reference
            "RFC 4451: BGP MED Considerations.";
        }
        leaf med-multiplier {
          type uint16;
          default 1;
          description
            "Specifies a MED multiplier.";
          reference
            "RFC 4451: BGP MED Considerations.";
        }
        description
          "The med-plus-igp option enables BGP to use the sum of
           MED multiplied by a MED multiplier and IGP cost multiplied
           by IGP cost multiplier to select routes when MED is
           required to determine the optimal route.";
      }
    }
  }

  grouping state {
    description
      "Grouping containing common counters relating to prefixes and
       paths";

    container statistics {
      config false;
      description
        "Global level statistics.";

      leaf total-paths {
        type yang:gauge32;
        description
          "Total number of BGP paths (BGP routes) within the
           context";
      }

      leaf total-prefixes {
        type yang:gauge32;
        description
          "Total number of BGP prefixes (destinations) received
           within the context";
      }
    }
  }

  grouping neighbor-group-route-reflector {
    description
      "Grouping used to include route reflector configuration and
       state for both BGP neighbors and peer groups";
    container route-reflector {
      description
        "Route reflector parameters for the BGP peer-group";
      reference
        "RFC 4456: BGP Route Reflection.";
      leaf cluster-id {
        type ibt:rr-cluster-id-type;
        description
          "Route Reflector cluster id to use when local router is
           configured as a route reflector.  Commonly set at the
           group level, but allows a different cluster id to be set
           for each neighbor.";
        reference
          "RFC 4456: BGP Route Reflection: An Alternative to
                     Full Mesh.";
      }
      leaf client {
        type boolean;
        default "false";
        description
          "Configure the neighbor as a route reflector client.";
        reference
          "RFC 4456: BGP Route Reflection: An Alternative to
                     Full Mesh.";
      }
    }
  }

  grouping neighbor-group-as-path-options {
    description
      "Grouping used to include AS_PATH manipulation configuration
       and state for both BGP neighbors and peer groups";
    container as-path-options {
      description
        "AS_PATH manipulation parameters for the BGP neighbor or
         group";
      leaf allow-own-as {
        type uint8;
        default "0";
        description
          "Specify the number of occurrences of the local BGP
           speaker's AS that can occur within the AS_PATH before it
           is rejected as looped.";
      }
      leaf replace-peer-as {
        type boolean;
        default "false";
        description
          "Replace occurrences of the peer's AS in the AS_PATH with
           the local autonomous system number";
      }
      leaf disable-peer-as-filter {
        type boolean;
        default "false";
        description
          "When set to true, the system advertises routes to a peer
           even if the peer's AS was in the AS path.  The default
           behavior (false) suppresses advertisements to peers if
           their AS number is in the AS path of the route.";
      }
    }
  }

  grouping add-paths {
    description
      "Grouping used to include ADD-PATHs configuration and state.";
    container add-paths {
      if-feature "ibt:add-paths";
      description
        "Parameters relating to the advertisement and receipt of
         multiple paths for a single NLRI (add-paths)";
      reference
        "RFC 7911: Advertisements of Multiple Paths in BGP.";
      leaf receive {
        type boolean;
        default "false";
        description
          "Enable ability to receive multiple path advertisements for
           an NLRI from the neighbor or group";
      }
      choice send {
        description
          "Choice of sending the max. number of paths or to send
           all.";
        case max {
          leaf max {
            type uint8;
            description
              "The maximum number of paths to advertise to neighbors
               for a single NLRI";
          }
        }
        case all {
          leaf all {
            type empty;
            description
              "Send all the path advertisements to neighbors for a
               single NLRI.";
          }
        }
      }
      leaf eligible-prefix-policy {
        type leafref {
          path "/rt-pol:routing-policy/rt-pol:policy-definitions/"
             + "rt-pol:policy-definition/rt-pol:name";
        }
        description
          "A reference to a routing policy which can be used to
           restrict the prefixes for which add-paths is enabled";
      }
    }
  }

  grouping dynamic-peers {
    description
      "Grouping to contain dynamic BGP peers. Dynamic peers are
       configured from a list of IP prefixes matching the IP source
       address of the dynamic peer.";

    container dynamic-peers {
      description
        "Configuration and operational state for dynamically
         configured peers.";

      list dynamic-peer {
        key "prefix";
        description
          "List of peers by IP prefix for this configuration scope
           that are dynamically configured.";

        leaf prefix {
          type inet:ip-prefix;
          description
            "Prefix for dynamic peer at this configuration scope.";
        }
      }
    }
  }
}
