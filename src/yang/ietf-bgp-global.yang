submodule ietf-bgp-global {
  yang-version "1.1";
  belongs-to ietf-bgp {
    prefix bgp;
  }

  import ietf-inet-types { 
    prefix inet; 
  }

  include ietf-bgp-common;
  include ietf-bgp-common-multiprotocol;
  
  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "This sub-module contains groupings that are specific to the
     global context of the BGP module";

  revision "YYYY-MM-DD" {
    description
      "Initial Version";
    reference 
      "RFC XXX, BGP Model for Service Provider Network.";
  }

  grouping bgp-global-default-route-distance-config {
    description
      "Configuration options relating to the administrative distance
      (or preference) assigned to routes received from different
      sources (external, internal, and local).";

    leaf external-route-distance {
      type uint8 {
        range "1..255";
      }
      description
        "Administrative distance for routes learned from external
        BGP (eBGP).";
    }
    leaf internal-route-distance {
      type uint8 {
        range "1..255";
      }
      description
        "Administrative distance for routes learned from internal
        BGP (iBGP).";
    }
  }

  grouping bgp-global-confederation-config {
    description
      "Configuration options specifying parameters when the local
      router is within an autonomous system which is part of a BGP
      confederation.";

    leaf enabled {
      type boolean;
      description
        "When this leaf is set to true it indicates that
        the local-AS is part of a BGP confederation";
    }

    leaf identifier {
      type inet:as-number;
      description
        "Confederation identifier for the autonomous system.";
    }

    leaf-list member-as {
      type inet:as-number;
      description
        "Remote autonomous systems that are to be treated
        as part of the local confederation.";
    }
  }

  grouping bgp-global-afi-safi-list {
    description
      "List of address-families associated with the BGP instance";

    list afi-safi {
      key "afi-safi-name";

      description
        "AFI,SAFI configuration available for the
        neighbour or group";

      uses mp-afi-safi-config;
      uses state;

      container graceful-restart {
        description
          "Parameters relating to BGP graceful-restart";
  
        uses mp-afi-safi-graceful-restart-config;
      }

      uses route-selection-options;
      uses global-group-use-multiple-paths;
      uses mp-all-afi-safi-list-contents;
    }
  }
}
