submodule ietf-bgp-capabilities {
  yang-version 1.1;
  belongs-to ietf-bgp {
    prefix bgp;
  }

  import iana-bgp-capabilities {
    prefix bc;
    reference
      "RFC XXXX: YANG Model for Border Gateway Protocol (BGP-4).";
  }
  import iana-bgp-afi-safi-types {
    prefix bast;
    reference
      "RFC XXXX: YANG Model for Border Gateway Protocol (BGP-4).";
  }
  import ietf-bgp-types {
    prefix ibt;
    reference
      "RFC XXXX: YANG Model for Border Gateway Protocol (BGP-4).";
  }
  import iana-routing-types {
    prefix iana-rt-types;
    reference
      "RFC 8294: Common YANG Data Types for the Routing Area.";
  }
  import ietf-inet-types {
    prefix inet;
    reference
      "RFC 9911: Common YANG Data Types.";
  }
  import ietf-yang-semver {
    prefix ysv;
    reference
      "I-D.ietf-netmod-yang-semver: YANG Semantic Versioning";
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This sub-module contains groupings that are used for BGP
     Capabilities within the BGP module.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    ysv:version 0.0.9;
    reference
      "RFC XXXX: YANG Model for Border Gateway Protocol (BGP-4).";
  }

  grouping bgp-capabilities-common {
    description
      "BGP Capabilities that are used commonly by the
       advertised-capability and received-capability lists in the
       bgp-capabilities grouping.";

    leaf code {
      type uint8 {
        range 1..255;
      }
      description
        "BGP Capability Code";
      reference
        "RFC 5492: Capabilities Advertisement with BGP-4, Section
         4.";
    }
    leaf index {
      type uint8;
      description
        "Multiple BGP Capabilities with a given Capability Code may
         be advertised in a BGP OPEN message.  This index permits
         multiple such Capabilities to be represented in the YANG
         model.  It is RECOMMENDED that this index start at one (1)
         and increase by one for each additional instance of the
         Capability.";
      reference
        "RFC 5492: Capabilities Advertisement with BGP-4, Section
         4.";
    }
    leaf name {
      type identityref {
        base bc:bgp-capability;
      }
      description
        "When known, name carries the bgp-capability identity for the
         AFI/SAFI combination as used in the BGP YANG modules.";
    }

    container value {
      description
        "Some BGP Capabilities carry a Capability-specific Capability
         Value.";
      reference
        "RFC 5492: Capabilities Advertisement with BGP-4, Section
         4.";

      container mpbgp {
        when "derived-from-or-self(../../bgp:name, 'bc:mp-bgp')";
        description
          "Multi-Protocol BGP-specific values.";
        reference
          "RFC 4760: Multiprotocol Extensions for BGP-4, Section 8.";

        leaf afi {
          type iana-rt-types:address-family;
          description
           "Address Family Identifier carried in the Multiprotocol
            Extensions Capability.";
          reference
            "RFC 4760: Multiprotocol Extensions for BGP-4, Section
             8.";
        }
        leaf safi {
          type iana-rt-types:bgp-safi;
          description
           "Subsequent Address Family Identifier carried in the
            Multiprotocol Extensions Capability.";
          reference
            "RFC 4760: Multiprotocol Extensions for BGP-4, Section
             8.";
        }
        leaf name {
          type identityref {
            base bast:afi-safi-type;
          }
          description
            "When known, name carries the BGP AFI-SAFI identity for
             the AFI/SAFI combination as used in the BGP YANG
             modules.";
        }
      }

      container graceful-restart {
        when "derived-from-or-self(../../bgp:name, " +
             "'bc:graceful-restart')";
        description
          "BGP Graceful Restart-specific values.";
        reference
          "RFC 4724: Graceful Restart Mechanism for BGP.";

        leaf flags {
          type ibt:graceful-restart-flags;
          description
            "Restart Flags advertised by the Graceful Restart
             Capability";
          reference
            "RFC 4724: Graceful Restart Mechanism for BGP, Section
             3.";
        }

        leaf unknown-flags {
          type bits {
            bit unknown-2 {
              position 2;
              description
                "Bit 2 was received but is currently RESERVED.";
            }
            bit unknown-3 {
              position 3;
              description
                "Bit 3 was received but is currently RESERVED.";
            }
          }
          description
            "When a bit is exchanged in the Graceful Restart Flags
             field that is unknown to this module, their bit position
             is rendered using the associated unknown bit.";
          reference
            "RFC 4724: Graceful Restart Mechanism for BGP, Section
             3.";
        }

        leaf restart-time {
          type ibt:graceful-restart-time-type;
          description
            "The period of time (advertised by the peer) that the
             peer expects a restart of a BGP session to take.";
          reference
            "RFC 4724: Graceful Restart Mechanism for BGP, Section
             3.";
        }

        list afi-safi {
          description
            "List of AFI/SAFIs advertised by the BGP Graceful Restart
             Capability and their AFI/SAFI-specific Flags.";
          leaf afi {
            type iana-rt-types:address-family;
            description
              "Address Family advertised in the BGP Graceful Restart
               Capability.";
            reference
              "RFC 4724: Graceful Restart Mechanism for BGP, Section
               3.";
          }
          leaf safi {
            type iana-rt-types:bgp-safi;
            description
              "Subsequent Address Family advertised in the BGP
               Graceful Restart Capability.";
            reference
              "RFC 4724: Graceful Restart Mechanism for BGP, Section
               3.";
          }
          leaf afi-safi-flags {
            type ibt:graceful-restart-flags-for-afi;
            description
              "Flags for Address Family advertised per-AFI/SAFI in
               the BGP Graceful Restart Capability.";
            reference
              "RFC 4724: Graceful Restart Mechanism for BGP, Section
               3.";
          }
          leaf afi-safi-unknown-flags {
            type bits {
              bit unknown-1 {
                position 1;
                description
                  "Bit 1 was received but is currently RESERVED.";
              }
              bit unknown-2 {
                position 2;
                description
                  "Bit 2 was received but is currently RESERVED.";
              }
              bit unknown-3 {
                position 3;
                description
                  "Bit 3 was received but is currently RESERVED.";
              }
              bit unknown-4 {
                position 4;
                description
                  "Bit 4 was received but is currently RESERVED.";
              }
              bit unknown-5 {
                position 5;
                description
                  "Bit 5 was received but is currently RESERVED.";
              }
              bit unknown-6 {
                position 6;
                description
                  "Bit 6 was received but is currently RESERVED.";
              }
              bit unknown-7 {
                position 7;
                description
                  "Bit 7 was received but is currently RESERVED.";
              }
            }
            description
              "When a bit is exchanged in the Graceful Restart Flags
               for Address Family field that is unknown to this
               module, their bit position is rendered using the
               associated unknown bit.";
            reference
              "RFC 4724: Graceful Restart Mechanism for BGP, Section
               3.";
          }
        }
      }

      container asn32 {
        when "derived-from-or-self(../../bgp:name, 'bc:asn32')";
        description
          "Four-byte AS Number-specific values.";
        reference
          "RFC 6793: BGP Support for Four-Octet Autonomous System
           (AS) Number Space, Section 3.";

        leaf as {
          type inet:as-number;
          description
            "Four-byte AS Number carried by the Support for 4-octet
             AS number capability.";
          reference
            "RFC 6793: BGP Support for Four-Octet Autonomous System
             (AS) Number Space, Section 3.";
        }
      }

      container add-paths {
        when "derived-from-or-self(../../bgp:name, 'bc:add-paths')";
        description
          "BGP add-paths-specific values.";
        reference
          "RFC 7911: Advertisement of Multiple Paths in BGP.";

        list afi-safi {
          description
            "List of AFI/SAFIs advertised by the BGP ADD-PATH
             Capability and their AFI/SAFI-specific mode.";
          leaf afi {
            type iana-rt-types:address-family;
            description
              "Address Family Identifier for an instance of the BGP
               ADD-PATH Capability.";
            reference
              "RFC 7911: Advertisement of Multiple Paths in BGP,
               Section 4.";
          }
          leaf safi {
            type iana-rt-types:bgp-safi;
            description
              "Subsequent Address Family Identifier for an instance
               of the BGP ADD-PATH Capability.";
            reference
              "RFC 7911: Advertisement of Multiple Paths in BGP,
               Section 4.";
          }
          leaf mode {
            type enumeration {
              enum receive {
                value 1;
                description
                  "The sender of the capability is able to receive
                   multiple paths from its peer.";
                reference
                  "RFC 7911: Advertisement of Multiple Paths in BGP,
                   Section 4.";
              }
              enum send {
                value 2;
                description
                  "The sender of the capability is able to send
                   multiple paths to its peer.";
                reference
                  "RFC 7911: Advertisement of Multiple Paths in BGP,
                   Section 4.";
              }
              enum receive-send {
                value 3;
                description
                  "The sender of the capability is able both receive
                   and send multiple paths for its peer.";
                reference
                  "RFC 7911: Advertisement of Multiple Paths in BGP,
                   Section 4.";
              }
            }
            description
              "Send/Receive value for a per-AFI/SAFI instance of the
               ADD-PATH Capability.";
            reference
              "RFC 7911: Advertisement of Multiple Paths in BGP,
               Section 4.";
          }
        }
      }
    }
  }

  grouping bgp-capabilities {
    description
      "Structural grouping used to include BGP Capabiliites for BGP
       neghbors.";

    container capabilities {
      config false;
      description
        "BGP Capabilities per-neighbor.";
      reference
        "RFC 5492: Capabilities Advertisement with BGP-4.";

      list advertised-capability {
        key "code index";
        description
          "List of advertised BGP capabilities, per-peer.
           Identified by the Capability Code and an index.  The
           index covers the case where the same BGP Capability
           may be advertised more than once.";

        uses bgp-capabilities-common;
      }

      list received-capability {
        key "code index";
        description
          "List of received BGP capabilities, per-peer.
           Identified by the Capability Code and an index.  The
           index covers the case where the same BGP Capability
           may be advertised more than once.";

        uses bgp-capabilities-common;
      }

      leaf-list negotiated-capability {
        type identityref {
          base bc:bgp-capability;
        }
        description
          "Negotiated BGP capabilities.";
      }
    }
  }
}
