submodule ietf-bgp-common-multiprotocol {
  yang-version "1.1";
  belongs-to ietf-bgp {
    prefix "bgp";
  }

  import ietf-bgp-types { 
    prefix bt; 
  }
  import ietf-routing-policy { 
    prefix rpol; 
  }

  include ietf-bgp-common;

  // meta
  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "This sub-module contains groupings that are related to support
     for multiple protocols in BGP. The groupings are common across
     multiple contexts.";

  revision "YYYY-MM-DD" {
    description
      "Initial Version";
    reference 
      "RFC XXX, BGP Model for Service Provider Network.";
  }

  grouping mp-afi-safi-graceful-restart-config {
    description
      "BGP graceful restart parameters that apply on a per-AFI-SAFI
       basis";

    leaf enabled {
      type boolean;
      default false;
      description
        "This leaf indicates whether graceful-restart is enabled for
         this AFI-SAFI";
    }
  }

  grouping mp-afi-safi-config {
    description
      "Configuration parameters used for all BGP AFI-SAFIs";

    leaf afi-safi-name {
      type identityref {
        base bt:afi-safi-type;
      }
      description "AFI,SAFI";
    }

    leaf enabled {
      type boolean;
      default false;
      description
        "This leaf indicates whether the IPv4 Unicast AFI,SAFI is
        enabled for the neighbour or group";
    }
  }

  grouping mp-all-afi-safi-list-contents {
    description
      "A common grouping used for contents of the list that is used
      for AFI-SAFI entries";

    // import and export policy included for the afi/safi
    uses rpol:apply-policy-group;

    container ipv4-unicast {
      when "../afi-safi-name = 'bt:IPV4_UNICAST'" {
        description
          "Include this container for IPv4 Unicast specific
           configuration";
      }

      description
        "IPv4 unicast configuration options";

      // include common IPv[46] unicast options
      uses mp-ipv4-ipv6-unicast-common;

      // placeholder for IPv4 unicast  specific configuration
    }

    container ipv6-unicast {
      when "../afi-safi-name = 'bt:IPV6_UNICAST'" {
        description
          "Include this container for IPv6 Unicast specific
           configuration";
      }

      description
        "IPv6 unicast configuration options";

      // include common IPv[46] unicast options
      uses mp-ipv4-ipv6-unicast-common;

      // placeholder for IPv6 unicast specific configuration
      // options
    }

    container ipv4-labeled-unicast {
      when "../afi-safi-name = 'bt:IPV4_LABELED_UNICAST'" {
        description
          "Include this container for IPv4 Labeled Unicast specific
           configuration";
      }

      description
        "IPv4 Labeled Unicast configuration options";

      uses mp-all-afi-safi-common;

      // placeholder for IPv4 Labeled Unicast specific config
      // options
    }

    container ipv6-labeled-unicast {
      when "../afi-safi-name = 'bt:IPV6_LABELED_UNICAST'" {
        description
          "Include this container for IPv6 Labeled Unicast specific
           configuration";
      }

      description
        "IPv6 Labeled Unicast configuration options";

      uses mp-all-afi-safi-common;

      // placeholder for IPv6 Labeled Unicast specific config
      // options.
    }

    container l3vpn-ipv4-unicast {
      when "../afi-safi-name = 'bt:L3VPN_IPV4_UNICAST'" {
        description
          "Include this container for IPv4 Unicast L3VPN specific
           configuration";
      }

      description
        "Unicast IPv4 L3VPN configuration options";

      // include common L3VPN configuration options
      uses mp-l3vpn-ipv4-ipv6-unicast-common;

      // placeholder for IPv4 Unicast L3VPN specific config options.
    }

    container l3vpn-ipv6-unicast {
      when "../afi-safi-name = 'bt:L3VPN_IPV6_UNICAST'" {
        description
          "Include this container for unicast IPv6 L3VPN specific
           configuration";
      }

      description
        "Unicast IPv6 L3VPN configuration options";

      // include common L3VPN configuration options
      uses mp-l3vpn-ipv4-ipv6-unicast-common;

      // placeholder for IPv6 Unicast L3VPN specific configuration
      // options
    }

    container l3vpn-ipv4-multicast {
      when "../afi-safi-name = 'bt:L3VPN_IPV4_MULTICAST'" {
        description
          "Include this container for multicast IPv6 L3VPN specific
           configuration";
      }

      description
        "Multicast IPv4 L3VPN configuration options";

      // include common L3VPN multicast options
      uses mp-l3vpn-ipv4-ipv6-multicast-common;

      // placeholder for IPv4 Multicast L3VPN specific configuration
      // options
    }

    container l3vpn-ipv6-multicast {
      when "../afi-safi-name = 'bt:L3VPN_IPV6_MULTICAST'" {
        description
          "Include this container for multicast IPv6 L3VPN specific
           configuration";
      }
      description
        "Multicast IPv6 L3VPN configuration options";

      // include common L3VPN multicast options
      uses mp-l3vpn-ipv4-ipv6-multicast-common;

      // placeholder for IPv6 Multicast L3VPN specific configuration
      // options
    }

    container l2vpn-vpls {
      when "../afi-safi-name = 'bt:L2VPN_VPLS'" {
        description
          "Include this container for BGP-signalled VPLS specific
           configuration";
      }

      description
        "BGP-signalled VPLS configuration options";

      // include common L2VPN options
      uses mp-l2vpn-common;

      // placeholder for BGP-signalled VPLS specific configuration
      // options
    }

    container l2vpn-evpn {
      when "../afi-safi-name = 'bt:L2VPN_EVPN'" {
        description
          "Include this container for BGP EVPN specific
           configuration";
      }

      description
        "BGP EVPN configuration options";

      // include common L2VPN options
      uses mp-l2vpn-common;

      // placeholder for BGP EVPN specific configuration options
    }
  }

  // Common groupings across multiple AFI,SAFIs
  grouping mp-all-afi-safi-common {
    description
      "Grouping for configuration common to all AFI,SAFI";

    container prefix-limit {
      description
        "Parameters relating to the prefix limit for the AFI-SAFI";
      leaf max-prefixes {
        type uint32;
        description
          "Maximum number of prefixes that will be accepted from the
           neighbour";
      }
      leaf shutdown-threshold-pct {
        type bt:percentage;
        description
          "Threshold on number of prefixes that can be received from
           a neighbour before generation of warning messages or log
           entries. Expressed as a percentage of max-prefixes";
      }
        
      leaf restart-timer {
        type decimal64 {
          fraction-digits 2;
        }
        units "seconds";
        description
          "Time interval in seconds after which the BGP session is
           re-established after being torn down due to exceeding the
           max-prefix limit.";
      }
    }
  }

  grouping mp-ipv4-ipv6-unicast-common {
    description
      "Common configuration that is applicable for IPv4 and IPv6
      unicast";

    // include common afi-safi options.
    uses mp-all-afi-safi-common;

    // configuration options that are specific to IPv[46] unicast
    leaf send-default-route {
      type boolean;
      default "false";
      description
        "If set to true, send the default-route to the neighbour(s)";
    }
  }

  grouping mp-l3vpn-ipv4-ipv6-unicast-common {
    description
      "Common configuration applied across L3VPN for IPv4
       and IPv6";

    // placeholder -- specific configuration options that are generic
    // across IPv[46] unicast address families.
    uses mp-all-afi-safi-common;
  }

  grouping mp-l3vpn-ipv4-ipv6-multicast-common {
    description
      "Common configuration applied across L3VPN for IPv4
      and IPv6";

    // placeholder -- specific configuration options that are
    // generic across IPv[46] multicast address families.
    uses mp-all-afi-safi-common;
  }

  grouping mp-l2vpn-common {
    description
      "Common configuration applied across L2VPN address
      families";

    // placeholder -- specific configuration options that are
    // generic across L2VPN address families
    uses mp-all-afi-safi-common;
  }

  // Config groupings for common groups
  grouping mp-all-afi-safi-common-prefix-limit-config {
    description
      "Configuration parameters relating to prefix-limits for an
      AFI-SAFI";

  }
}
