module iana-bgp-rib-types {
  yang-version 1.1;
  namespace "urn:ietf:params:xml:ns:yang:iana-bgp-rib-types";
  prefix brt;

  import ietf-yang-semver {
    prefix ysv;
    reference
      "I-D.ietf-netmod-yang-semver: YANG Semantic Versioning";
  }

  organization
    "IANA";
  contact
    "Internet Assigned Numbers Authority

     Postal: ICANN
             12025 Waterfront Drive, Suite 300
             Los Angeles, CA 90094-2536
             United States of America
     Tel:    +1 310 301 5800
     <mailto:iana@iana.org>

     Authors: Mahesh Jethanandani (mjethanandani at gmail.com),
              Keyur Patel (keyur at arrcus.com),
              Susan Hares (shares at ndzh.com),
              Jeffrey Haas (jeffrey.haas at hpe.com).";

  description
    "This YANG module is maintained by IANA and defines identity
     and type definitions associated with BGP RIB route
     eligibility and path-selection status.  It reflects the
     'BGP Route Ineligibility Reasons', 'BGP Best-Path
     Non-Selection Reasons', and 'BGP Route Policy Non-Selection
     Reasons' registries at IANA.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     The initial version of this YANG module is part of RFC XXXX;
     see the RFC itself for full legal notices.

     The most recent version of this YANG module is available at
     <https://www.iana.org/assignments/iana-bgp-rib-types>.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    ysv:version 0.0.9;
    reference
      "RFC XXXX: YANG Model for Border Gateway Protocol (BGP-4).";
  }

  identity ineligible-route-reason {
    description
      "Base identity for reason code for routes that are rejected as
       ineligible. Some derived entities are based on BMP v3.";
    reference
      "RFC 7854: BGP Monitoring Protocol.";
  }

  identity ineligible-cluster-loop {
    base ineligible-route-reason;
    description
      "Route was ineligible due to CLUSTER_LIST loop";
  }

  identity ineligible-as-loop {
    base ineligible-route-reason;
    description
      "Route was ineligible due to AS_PATH loop";
  }

  identity ineligible-originator {
    base ineligible-route-reason;
    description
      "Route was ineligible due to ORIGINATOR_ID. For example, update
       has local router as originator";
  }

  identity ineligible-confed {
    base ineligible-route-reason;
    description
      "Route was ineligible due to a loop in the AS_CONFED_SEQUENCE
       or AS_CONFED_SET attributes";
  }

  identity bgp-not-selected-bestpath {
    description
      "Base identity for indicating reason a route was was not
       selected by BGP route selection algorithm";
    reference
      "RFC 4271: A Border Gateway Protocol 4 (BGP-4), Section 9.1.";
  }

  identity local-pref-lower {
    base bgp-not-selected-bestpath;
    description
      "Route has a lower localpref attribute than current best path";
    reference
      "RFC 4271: A Border Gateway Protocol 4 (BGP-4),
       Section 9.1.2.";
  }

  identity as-path-longer {
    base bgp-not-selected-bestpath;
    description
      "Route has a longer AS path attribute than current best path";
    reference
      "RFC 4271: A Border Gateway Protocol 4 (BGP-4),
       Section 9.1.2.2 (a).";
  }

  identity origin-type-higher {
    base bgp-not-selected-bestpath;
    description
      "Route has a higher origin type, i.e., IGP origin is preferred
       over EGP or incomplete";
    reference
      "RFC 4271: A Border Gateway Protocol 4 (BGP-4),
       Section 9.1.2.2 (b).";
  }

  identity med-higher {
    base bgp-not-selected-bestpath;
    description
      "Route has a higher MED, or metric, attribute than the current
       best path";
    reference
      "RFC 4271: A Border Gateway Protocol 4 (BGP-4),
       Section 9.1.2.2 (c).";
  }

  identity prefer-external {
    base bgp-not-selected-bestpath;
    description
      "Route source is via IBGP, rather than EGP.";
    reference
      "RFC 4271: A Border Gateway Protocol 4 (BGP-4),
       Section 9.1.2.2 (d).";
  }

  identity nexthop-cost-higher {
    base bgp-not-selected-bestpath;
    description
      "Route has a higher interior cost to the next hop.";
    reference
      "RFC 4271: A Border Gateway Protocol 4 (BGP-4),
       Section 9.1.2.2 (e).";
  }

  identity higher-router-id {
    base bgp-not-selected-bestpath;
    description
      "Route was sent by a peer with a higher BGP Identifier value.";
    reference
      "RFC 4271: A Border Gateway Protocol 4 (BGP-4),
       Section 9.1.2.2 (f).";
  }

  identity higher-peer-address {
    base bgp-not-selected-bestpath;
    description
      "Route was sent by a peer with a higher IP address";
    reference
      "RFC 4271: A Border Gateway Protocol 4 (BGP-4),
       Section 9.1.2.2 (g).";
  }

  identity bgp-not-selected-policy {
    description
      "Base identity for reason code for routes that are rejected
       due to policy";
  }

  identity rejected-import-policy {
    base bgp-not-selected-policy;
    description
      "Route was rejected after applying import policies.";
  }
}
