module ietf-bgp-policy {
  yang-version 1.1;
  namespace "urn:ietf:params:xml:ns:yang:ietf-bgp-policy";
  prefix bp;

  // import some basic types

  import ietf-inet-types {
    prefix inet;
    reference
      "RFC 9911: Common YANG Data Types";
  }
  import ietf-routing-policy {
    prefix rt-pol;
    reference
      "RFC 9067: A YANG Data Model for Routing Policy";
  }
  import iana-bgp-afi-safi-types {
    prefix bast;
    reference
      "RFC XXXX: YANG Model for Border Gateway Protocol (BGP-4).";
  }
  import ietf-bgp-types {
    prefix ibt;
    reference
      "RFC XXXX: YANG Model for Border Gateway Protocol (BGP-4).";
  }
  import iana-bgp-community-types {
    prefix bct;
    reference
      "RFC XXXX: YANG Model for Border Gateway Protocol (BGP-4).";
  }
  import ietf-bgp-community-types {
    prefix ibct;
    reference
      "RFC XXXX: YANG Model for Border Gateway Protocol (BGP-4).";
  }
  import ietf-yang-semver {
    prefix ysv;
    reference
      "I-D.ietf-netmod-yang-semver: YANG Semantic Versioning";
  }

  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This module contains data definitions for BGP routing policy.
     It augments the base routing-policy module with BGP-specific
     options for conditions and actions.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    ysv:version 0.0.9;
    reference
      "RFC XXXX: YANG Model for Border Gateway Protocol (BGP-4).";
  }

  /*
   * typedef statements
   */

  typedef bgp-set-community-option-type {
    type enumeration {
      enum add {
        description
          "Add the specified communities to the existing
           community attribute.";
      }
      enum remove {
        description
          "Remove the specified communities from the
           existing community attribute.";
      }
      enum replace {
        description
          "Replace the existing community attribute with
           the specified communities. If an empty set is
           specified, this removes the community attribute
           from the route.";
      }
    }
    description
      "Type definition for options when setting the community
       attribute in a policy action.";
  }

  typedef bgp-next-hop-type {
    type union {
      type inet:ip-address-no-zone;
      type enumeration {
        enum self {
          description
            "Special designation for local router's own
             address, i.e., next-hop-self.";
        }
      }
    }
    description
      "Type definition for specifying next-hop in policy actions.";
  }

  typedef bgp-set-med-type {
    type union {
      type string {
        pattern '[+-]'
              + '([0-9]|[1-9][0-9]{1,8}|[1-3][0-9]{9}|4[01][0-9]{8}|'
              + '42[0-8][0-9]{7}|429[0-3][0-9]{6}|4294[0-8][0-9]{5}|'
              + '42949[0-5][0-9]{4}|429496[0-6][0-9]{3}|'
              + '4294967[01][0-9]{2}|42949672[0-8][0-9]|'
              + '429496729[0-5])';
      }
      type enumeration {
        enum igp {
          description
            "Set the MED value to the IGP cost toward the
             next hop for the route.";
        }
        enum med-plus-igp {
          description
            "Before comparing MED values for path selection, adds to
             the MED the cost of the IGP route to the BGP next-hop
             destination.

             This option replaces the MED value for the router,
             but does not affect the IGP metric comparison. As a
             result, when multiple routes have the same value
             after the MED-plus-IPG comparison, and route selection
             continues, the IGP route metric is also compared, even
             though it was added to the MED value and compared
             earlier in the selection process.

             Useful when the downstream AS requires the complete
             cost of a certain route that is received across
             multiple ASs.";
        }
      }
      type uint32;
    }
    description
      "Type definition for specifying how the BGP MED can
       be set in BGP policy actions. The three choices are to set
       the MED directly, increment/decrement using +/- notation,
       and setting it to the IGP cost (predefined value).";
  }

  grouping equality-operator {
    description
      "Grouping used for common equality operations in BGP policy.";
    choice operation {
      case eq {
        leaf eq {
          type empty;
          description
            "Check to see if the value is equal.";
        }
      }

      case lt-or-eq {
        leaf lt-or-eq {
          type empty;
          description
            "Check to see if the value is less than or equal.";
        }
      }

      case gt-or-eq {
        leaf gt-or-eq {
          type empty;
          description
            "Check to see if the value is greater than or
             equal.";
        }
      }
      description
        "Choice of operations on the value";
    }
  }

  // Identities

  // augment statements

  augment "/rt-pol:routing-policy/rt-pol:defined-sets" {
    description
      "Adds BGP defined sets container to routing policy model.";
    container bgp-defined-sets {
      description
        "BGP-related set definitions for policy match conditions.";
      container as-path-sets {
        description
          "Enclosing container for list of define AS path sets.";
        list as-path-set {
          key "name";
          description
            "List of defined AS path sets.";
          leaf name {
            type string;
            description
              "Name of the AS path set -- this is used to reference
               the set in match conditions.";
          }
          leaf-list member {
            type string;
            description
              "AS path regular expression using BGP YANG AS_PATH
               regular expression syntax.  If any of the regular
               expressions in the lists are matched, the as-path-set
               is considered matched.";
            reference
              "RFC XXXX: YANG Model for Border Gateway Protocol
               (BGP-4), Appendix F.3.";
          }
        }
      }

      container community-sets {
        description
          "Enclosing container for list of defined BGP community
           sets.";
        list community-set {
          key "name";
          description
            "List of defined BGP community sets.";
          leaf name {
            type string;
            description
              "Name / label of the community set -- this is used to
               reference the set in match conditions.";
          }
          leaf-list member {
            type union {
              type bct:bgp-well-known-community-type;
              type ibct:bgp-std-community-type;
              type ibct:bgp-community-regexp-type;
            }
            description
              "Members of the community set";
          }
        }
      }

      container ext-community-sets {
        description
          "Enclosing container for list of extended BGP community
           sets";
        list ext-community-set {
          key "name";
          description
            "List of defined extended BGP community sets";
          leaf name {
            type string;
            description
              "Name / label of the extended community set -- this is
               used to reference the set in match conditions";
          }
          leaf-list member {
            type union {
              type bct:bgp-ext-community-type;
              type ibct:bgp-community-regexp-type;
            }
            description
              "Members of the extended community set.";
          }
        }
      }

      container ipv6-ext-community-sets {
        description
          "Enclosing container for list of extended IPv6 BGP
           community sets";
        list ipv6-ext-community-set {
          key "name";
          description
            "List of defined IPv6 extended BGP community sets";
          leaf name {
            type string;
            description
              "Name / label of the IPv6 extended community set --
               this is used to reference the set in match
               conditions";
          }
          leaf-list member {
            type union {
              type bct:bgp-ipv6-ext-community-type;
              type ibct:bgp-community-regexp-type;
            }
            description
              "Members of the IPv6 extended community set.";
          }
        }
      }

      container large-community-sets {
        description
          "Enclosing container for list of large BGP community
           sets";
        list large-community-set {
          key "name";
          description
            "List of defined large BGP community sets";
          leaf name {
            type string;
            description
              "Name / label of the large community set -- this is
               used to reference the set in match conditions";
          }
          leaf-list member {
            type union {
              type ibct:bgp-large-community-type;
              type ibct:bgp-community-regexp-type;
            }
            description
              "Members of the large community set.";
          }
        }
      }

      container next-hop-sets {
        description
          "Definition of a list of IPv4 or IPv6 next-hops which can
           be matched in a routing policy.";

        list next-hop-set {
          key "name";
          description
            "List of defined next-hop sets for use in policies.";

          leaf name {
            type string;
            description
              "Name of the next-hop set.";
          }
          leaf-list next-hop {
            type bgp-next-hop-type;
            description
              "List of IP addresses in the next-hop set.";
          }
        }
      }
    }
  }

  augment "/rt-pol:routing-policy/rt-pol:policy-definitions/" +
          "rt-pol:policy-definition/rt-pol:statements/" +
          "rt-pol:statement/rt-pol:conditions" {
    description
      "BGP policy conditions added to routing policy module.";

    container bgp-conditions {
      description
        "Top-level container for BGP specific policy conditions.";

      container local-pref {
        description
          "Value and comparison operations for conditions based on
           the value of the BGP LOCAL_PREF.";
        reference
          "RFC 4271: A Border Gateway Protocol 4 (BGP-4), Section
           5.1.5.";

        leaf value {
          type uint32;
          description
            "BGP LOCAL_PREF value for comparison to the entry in the
             BGP route.";
        }
        
        uses equality-operator;
      }

      container med {
        description
          "Value and comparison operations for conditions based on
           the value of the BGP MULTI_EXIT_DISC (MED)";
        reference
          "RFC 4271: A Border Gateway Protocol 4 (BGP-4), Section
           5.1.4.";

        leaf value {
          type uint32;
          description
            "BGP MED value for comparison to the entry in the BGP
             route.";
        }

        uses equality-operator;
      }

      leaf origin-eq {
        type ibt:bgp-origin-attr-type;
        description
          "Condition to check if the route origin is equal to the
           specified value.";
      }

      container match-afi-safi {
        description
          "Match an address family according to the logic defined in
           the match-set-options leaf.";
        leaf-list afi-safi-in {
          type identityref {
            base bast:afi-safi-type;
          }
          description
            "List of address families which the NLRI may be within.";
        }
        uses rt-pol:match-set-options-restricted-group;
      }

      container match-neighbor {
        description
          "Match a neighbor according to the logic defined in the
           match-set-options leaf.";

        leaf-list neighbor-eq {
          type inet:ip-address;
          description
            "List of neighbor addresses to check for in the ingress
             direction.";
        }
        uses rt-pol:match-set-options-restricted-group;
      }

      leaf route-type {
        type enumeration {
          enum internal {
            description
              "route type is internal.";
          }
          enum external {
            description
              "route type is external.";
          }
        }
        description
          "Condition to check the route type in the route update.";
      }

      container community-count {
        description
          "Value and comparison operations for conditions based on
           the number of communities in the route update.";

        leaf value {
          type uint32;
          description
            "Value for the number of communities in the route
             update.";
        }

        uses equality-operator;
      }

      container extended-community-count {
        description
          "Value and comparison operations for conditions based on
           the number of extended communities in the route update.";

        leaf value {
          type uint32;
          description
            "Value for the number of communities in the route
             update.";
        }

        uses equality-operator;
      }

      container as-path-length {
        description
          "Value and comparison operations for conditions based on
           the length of the AS path in the route update.

           The as-path-length SHALL be calculated and SHALL follow
           RFC 4271 rules.";
        reference
          "RFC 4271: A Border Gateway Protocol 4 (BGP-4).";

        leaf value {
          type uint32;
          description
            "Value of the AS path length in the route update.";
        }

        uses equality-operator;
      }

      container match-community-set {
        description
          "Top-level container for match conditions on communities.
           Match a referenced community-set according to the logic
           defined in the match-set-options leaf.";
        leaf community-set {
          type leafref {
            path "/rt-pol:routing-policy/rt-pol:defined-sets/"
               + "bgp-defined-sets/community-sets/"
               + "community-set/name";
          }
          description
            "References a defined community set.";
        }
        uses rt-pol:match-set-options-group;
      }

      container match-ext-community-set {
        description
          "Match a referenced extended community-set according to the
           logic defined in the match-set-options leaf.";
        leaf ext-community-set {
          type leafref {
            path "/rt-pol:routing-policy/rt-pol:defined-sets/"
               + "bgp-defined-sets/ext-community-sets/"
               + "ext-community-set/name";
          }
          description
            "References a defined extended community set.";
        }
        leaf ext-community-match-kind {
          type enumeration {
            enum ext-community {
              description
                "Perform the match against the ext-community RIB
                 attribute.";
            }
            enum ext-community-raw {
              description
                "Perform the match against the ext-community-raw RIB
                 attribute.";
            }
          }
          default ext-community;
          description
            "Extended communities may be matched by the ext-community
             RIB attribute, or the ext-community-raw RIB attribute.
             This leaf selects which leaf to perform the match
             operation against.";
        }
        uses rt-pol:match-set-options-group;
      }

      container match-ipv6-ext-community-set {
        description
          "Match a referenced IPv6 extended community-set according
           to the logic defined in the match-set-options leaf.";
        leaf ipv6-ext-community-set {
          type leafref {
            path "/rt-pol:routing-policy/rt-pol:defined-sets/"
               + "bgp-defined-sets/ipv6-ext-community-sets/"
               + "ipv6-ext-community-set/name";
          }
          description
            "References a defined IPv6 extended community set.";
        }
        leaf ipv6-ext-community-match-kind {
          type enumeration {
            enum ipv6-ext-community {
              description
                "Perform the match against the IPv6 ext-community RIB
                 attribute.";
            }
            enum ipv6-ext-community-raw {
              description
                "Perform the match against the IPv6 ext-community-raw
                 RIB attribute.";
            }
          }
          default ipv6-ext-community;
          description
            "IPv6 Extended communities may be matched by the
             ipv6-ext-community RIB attribute, or the
             ipv6-ext-community-raw RIB attribute.  This leaf selects
             which leaf to perform the match operation against.";
        }
        uses rt-pol:match-set-options-group;
      }

      container match-large-community-set {
        description
          "Match a referenced large community-set according to the
           logic defined in the match-set-options leaf.";
        leaf large-community-set {
          type leafref {
            path "/rt-pol:routing-policy/rt-pol:defined-sets/"
               + "bgp-defined-sets/large-community-sets/"
               + "large-community-set/name";
          }
          description
            "References a defined large community set.";
        }
        uses rt-pol:match-set-options-group;
      }

      container match-as-path-set {
        description
          "Match a referenced as-path set according to the logic
           defined in the match-set-options leaf.";
        leaf as-path-set {
          type leafref {
            path "/rt-pol:routing-policy/rt-pol:defined-sets/"
               + "bgp-defined-sets/as-path-sets/"
               + "as-path-set/name";
          }
          description
            "References a defined AS path set";
        }
        uses rt-pol:match-set-options-group;
      }

      container match-next-hop-set {
        description
          "Match a referenced next-hop set according to the logic
           defined in the match-set-options leaf.";
        leaf next-hop-set {
          type leafref {
            path "/rt-pol:routing-policy/rt-pol:defined-sets/"
               + "bgp-defined-sets/next-hop-sets/"
               + "next-hop-set/name";
          }
          description
            "Reference a defined next-hop set.";
        }
        uses rt-pol:match-set-options-restricted-group;
      }
    }
  }

  augment "/rt-pol:routing-policy/rt-pol:policy-definitions/" +
          "rt-pol:policy-definition/rt-pol:statements/" +
          "rt-pol:statement/rt-pol:actions" {
    description
      "BGP policy actions added to routing policy module.";
    container bgp-actions {
      description
        "Top-level container for BGP-specific actions";
      leaf set-route-origin {
        type ibt:bgp-origin-attr-type;
        description
          "Set the origin attribute to the specified value";
      }
      leaf set-local-pref {
        type uint32;
        description
          "Set the local pref attribute on the route.";
      }
      leaf set-next-hop {
        type bgp-next-hop-type;
        description
          "Set the next-hop attribute in the route.";
      }
      leaf set-med {
        type bgp-set-med-type;
        description
          "Set the med metric attribute in the route.";
      }

      container set-as-path-prepend {
        description
          "Action to prepend local AS number to the AS-path a
           specified number of times";

        leaf repeat-n {
          type uint8 {
            range "1..max";
          }
          description
            "Number of times to prepend the AS number to the AS
             path. If no value is specified by the asn or use-last-as
             leafs, the local AS number is used. The value should be
             between 1 and the maximum supported by the
             implementation.";
        }
        leaf asn {
          type inet:as-number;
          must "../repeat-n and not(../use-last-as)";
          description
            "The AS number to prepend to the AS path. If neither this
             leaf nor use-last-as leaf is specified, but repeat-n is
             set, then the local AS number will be used for
             prepending.";
        }
        leaf use-last-as {
          type boolean;
          must "../repeat-n and not(../asn)";
          description
            "Indicates whether to use the last AS number, which is
             also the most recent AS number, to prepend to the AS
             path.  If neither this leaf, nor asn leaf is specified,
             but repeat-n is set, then the local AS number will be
             used for prepending.";
        }
      }

      container set-community {
        description
          "Action to set the community attributes of the route, along
           with options to modify how the community is modified.
           Communities may be set using an inline list OR
           reference to an existing defined set (not both).";

        leaf options {
          type bgp-set-community-option-type;
          description
            "Options for modifying the community attribute with
             the specified values.  These options apply to both
             methods of setting the community attribute.";
        }

        choice method {
          description
            "Indicates the method used to specify the extended
             communities for the set-community action";
          case inline {
            leaf-list community {
              type union {
                type bct:bgp-well-known-community-type;
                type ibct:bgp-std-community-type;
              }
              description
                "Set the community values for the update inline with
                 a list.";
            }
          }

          case reference {
            leaf community-set-ref {
              type leafref {
                path "/rt-pol:routing-policy/rt-pol:defined-sets/"
                   + "bgp-defined-sets/"
                   + "community-sets/community-set/name";
              }
              description
                "References a defined community set by name";
            }
          }
        }
      }

      container set-ext-community {
        description
          "Action to set the extended community attributes of the
           route, along with options to modify how the community is
           modified. Extended communities may be set using an inline
           list OR a reference to an existing defined set (but not
           both).";

        leaf options {
          type bgp-set-community-option-type;
          description
            "Options for modifying the community attribute with
             the specified values.  These options apply to both
             methods of setting the community attribute.";
        }

        choice method {
          description
            "Indicates the method used to specify the extended
             communities for the set-ext-community action";
          case inline {
            leaf-list community {
              type bct:bgp-ext-community-type;
              description
                "Set the extended community values for the update
                 inline with a list.";
            }
          }
          case reference {
            leaf ext-community-set-ref {
              type leafref {
                path "/rt-pol:routing-policy/rt-pol:defined-sets/"
                   + "bgp-defined-sets/ext-community-sets/"
                   + "ext-community-set/name";
              }
              description
                "References a defined extended community set by
                 name.";
            }
          }
        }
      }

      container set-ipv6-ext-community {
        description
          "Action to set the IPv6 extended community attributes of
           the route, along with options to modify how the community
           is modified. IPv6 extended communities may be set using an
           inline list OR a reference to an existing defined set (but
           not both).";

        leaf options {
          type bgp-set-community-option-type;
          description
            "Options for modifying the community attribute with
             the specified values.  These options apply to both
             methods of setting the community attribute.";
        }

        choice method {
          description
            "Indicates the method used to specify the IPv6 extended
             communities for the set-ipv6-ext-community action";
          case inline {
            leaf-list community {
              type bct:bgp-ipv6-ext-community-type;
              description
                "Set the IPv6 extended community values for the
                 update inline with a list.";
            }
          }
          case reference {
            leaf ipv6-ext-community-set-ref {
              type leafref {
                path "/rt-pol:routing-policy/rt-pol:defined-sets/"
                   + "bgp-defined-sets/ipv6-ext-community-sets/"
                   + "ipv6-ext-community-set/name";
              }
              description
                "References a defined IPv6 extended community set by
                 name.";
            }
          }
        }
      }

      container set-large-community {
        description
          "Action to set the large community attributes of the
           route, along with options to modify how the community is
           modified. Large communities may be set using an inline
           list OR a reference to an existing defined set (but not
           both).";

        leaf options {
          type bgp-set-community-option-type;
          description
            "Options for modifying the community attribute with
             the specified values. These options apply to both
             methods of setting the community attribute.";
        }

        choice method {
          description
            "Indicates the method used to specify the large
             communities for the set-large-community action";
          case inline {
            leaf-list community {
              type ibct:bgp-large-community-type;
              description
                "Set the large community values for the update
                 inline with a list.";
            }
          }
          case reference {
            leaf large-community-set-ref {
              type leafref {
                path "/rt-pol:routing-policy/rt-pol:defined-sets/"
                   + "bgp-defined-sets/large-community-sets/"
                   + "large-community-set/name";
              }
              description
                "References a defined extended community set by
                 name.";
            }
          }
        }
      }
    }
  }
}
