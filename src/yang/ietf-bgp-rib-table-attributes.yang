submodule ietf-bgp-rib-table-attributes {
  yang-version 1.1;
  belongs-to ietf-bgp {
    prefix br;
  }

  // import some basic types

  import ietf-yang-types {
    prefix types;
    reference
      "RFC 6991, Common YANG Data Types.";
  }
  include ietf-bgp-rib-types;

  organization
    "IETF IDR Working Group";
  contact
    "WG Web:   <http://tools.ietf.org/wg/idr>
     WG List:  <idr@ietf.org>

     Authors: Mahesh Jethanandani (mjethanandani at gmail.com),
              Keyur Patel (keyur at arrcus.com),
              Susan Hares (shares at ndzh.com,
              Jeffrey Haas (jhaas at juniper.net).";
  description
    "This submodule contains common data definitions for data
     related to a RIB entry, or RIB table.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial version.";
    reference
      "RFC XXXX: BGP YANG Model for Service Provider Network.";
  }

  grouping bgp-common-route-annotations-state {
    description
      "Data definitions for flags and other information attached
       to routes in both LOC-RIB and Adj-RIB";
    leaf last-modified {
      type types:timeticks;
      description
        "Timestamp when this path was last modified.

         The value is the timestamp in seconds relative to
         the Unix Epoch (Jan 1, 1970 00:00:00 UTC).";
    }
    leaf valid-route {
      type boolean;
      description
        "Indicates that the route is considered valid by the
         local router";
    }
    leaf invalid-reason {
      type identityref {
        base invalid-route-reason;
      }
      description
        "If the route is rejected as invalid, this indicates the
         reason.";
    }
  }

  grouping bgp-adj-rib-in-post-route-annotations-state {
    description
      "Data definitions for information attached to routes in the
       Adj-RIB-in post-policy table";
    leaf best-path {
      type boolean;
      description
        "Current path was selected as the best path.";
    }
  }
}
