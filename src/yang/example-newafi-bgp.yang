module example-newafi-bgp {
  yang-version 1.1;
  namespace "http://example.com/ns/example-newafi-bgp";
  prefix example-newafi-bgp;

  import ietf-inet-types {
    prefix inet;
    reference
      "RFC 9911: Common YANG Data Types.";
  }
  
  import ietf-routing {
    prefix rt;
    reference
      "RFC 8349, A YANG Data Model for Routing Management
       (NMDA Version)";
  }

  import ietf-bgp {
    prefix "bgp";
    reference
      "RFC XXXX: YANG module for Border Gateway Protocol (BGP).";
  }

  import iana-bgp-afi-safi-types {
    prefix bast;
  }

  organization
    "Newafi model group.";

  contact
    "abc@example.com";
  description
    "This YANG module defines and uses new AFI.";

  revision YYYY-MM-DD {
    description
      "Creating new AFI and using in this model";

    reference
      "RFC XXXX: YANG module for Border Gateway Protocol (BGP).";
  }

  identity foo {
    base bast:afi-safi-type;
    description
      "New AFI type foo.";
  }

  augment "/rt:routing/rt:control-plane-protocols/" +
          "rt:control-plane-protocol/bgp:bgp/bgp:global/" +
          "bgp:afi-safis/bgp:afi-safi" {
    when "derived-from-or-self(bgp:name, 'example-newafi-bgp:foo')" {
      description
        "This augmentation is valid for a AFI/SAFI instance
         of 'foo'";
    }
    container foo {
      description
        "Container to add 'foo' specific AFI/SAFI information.
         First add the common stuff.";
      uses bgp:mp-all-afi-safi-common;
    }
  }

  augment "/rt:routing/rt:control-plane-protocols/" +
          "rt:control-plane-protocol/bgp:bgp/" +
          "bgp:rib/bgp:afi-safis/bgp:afi-safi" {
    when "derived-from-or-self(bgp:name, 'example-newafi-bgp:foo')" {
      description
        "This augmentation is valid for a AFI/SAFI instance
         of 'foo'";
    }

    container foo {
      description
        "Container to add 'foo' rib specific information.
         First add the common stuff.";
      container loc-rib {
        config false;
        description
          "Container for the 'foo' BGP LOC-RIB data.";
        container routes {
          description
            "Enclosing container for list of routes in the routing
             table.";
          list route {
            key "prefix origin path-id";
            description
              "List of routes in the table, keyed by the route
               prefix, the route origin, and path-id.  The route
               origin can be either the neighbor address from which
               the route was learned, or the source protocol that
               injected the route.  The path-id distinguishes routes
               for the same prefix received from a neighbor (e.g.,
               if add-paths is enabled).";
            leaf prefix {
	      type inet:ip-address;
              description
                "The 'foo' prefix corresponding to the route.";
            }
            uses bgp:bgp-loc-rib-common-keys;
            uses bgp:bgp-loc-rib-common-attr-refs;
            uses bgp:bgp-common-route-annotations-state;
            uses bgp:bgp-unknown-attr-top;
            uses bgp:rib-ext-route-annotations;
          }
          uses bgp:clear-routes;
        }
      }

      container neighbors {
        config false;
        description
          "Enclosing container for neighbor list.";
        list neighbor {
          key "neighbor-address";
          description
            "List of neighbors (peers) of the local BGP speaker.";
          leaf neighbor-address {
            type inet:ip-address;
            description
              "IP address of the BGP neighbor or peer.";
          }
          container adj-rib-in-pre {
            description
	      "Per-neighbor table containing the NLRI updates
	       received from the neighbor before any local input
	       policy rules or filters have been applied.  This can
	       be considered the 'raw' updates from the neighbor.";
            uses bgp:ipv4-adj-rib-common;
          }
          container adj-rib-in-post {
            description
	      "Per-neighbor table containing the paths received from
	       the neighbor that are eligible for best-path selection
	       after local input policy rules have been applied.";
            uses bgp:ipv4-adj-rib-in-post;
          }
          container adj-rib-out-pre {
            description
	      "Per-neighbor table containing paths eligible for
	       sending (advertising) to the neighbor before output
	       policy rules have been applied.";
            uses bgp:ipv4-adj-rib-common;
          }
          container adj-rib-out-post {
            description
	      "Per-neighbor table containing paths eligible for
	       sending (advertising) to the neighbor after output
	       policy rules have been applied.";
            uses bgp:ipv4-adj-rib-common;
          }
        }
      }
    }
  }
}
