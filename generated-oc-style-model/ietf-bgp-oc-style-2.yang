module ietf-bgp-oc-style {
  yang-version 1;
  namespace "urn:ietf:params:xml:ns:yang:ietf-bgp";
  prefix bgp;

  import ietf-routing-policy {
    prefix rpol;
  }
  import ietf-inet-types {
    prefix inet;
  }
  import ietf-bgp-types {
    prefix bgp-types;
  }
  import ietf-yang-types {
    prefix yang;
  }

  organization
    "OpenConfig working group";
  contact
    "OpenConfig working group
     netopenconfig@googlegroups.com";
  description
    "This module describes a YANG model for BGP protocol
     configuration.It is a limited subset of all of the configuration
     parameters available in the variety of vendor implementations,
     hence it is expected that it would be augmented with vendor-
     specific configuration data as needed. Additional modules or
     submodules to handle other aspects of BGP configuration,
     including policy, VRFs, VPNs, and additional address families
     are also expected.
     
     This model supports the following BGP configuration level
     hierarchy:
     
      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]";

  revision 2016-06-21 {
    description
      "OpenConfig BGP refactor";
    reference "2.1.1";
  }
  revision 2016-06-06 {
    description
      "OpenConfig public release";
    reference "2.1.0";
  }
  revision 2016-03-31 {
    description
      "OpenConfig public release";
    reference "2.0.1";
  }

  container bgp {
    description
      "Top-level configuration and state for the BGP router";
    container global {
      description
        "Global configuration for the BGP router";
      container config {
        description
          "Contains intended configuration";
        leaf as {
          type inet:as-number;
          mandatory true;
          description
            "Local autonomous system number of the router.  Uses
             the 32-bit as-number type from the model in RFC 6991.";
        }
        leaf router-id {
          type yang:dotted-quad;
          description
            "Router id of the router - an unsigned 32-bit integer
             expressed in dotted quad notation.";
          reference
            "RFC4271 - A Border Gateway Protocol 4 (BGP-4),
             Section 4.2";
        }
      }
      container state {
        config false;
        description
          "Contains applied configuration and derived state";
        leaf as {
          type inet:as-number;
          mandatory true;
          description
            "Local autonomous system number of the router.  Uses
             the 32-bit as-number type from the model in RFC 6991.";
        }
        leaf router-id {
          type yang:dotted-quad;
          description
            "Router id of the router - an unsigned 32-bit integer
             expressed in dotted quad notation.";
          reference
            "RFC4271 - A Border Gateway Protocol 4 (BGP-4),
             Section 4.2";
        }
        leaf total-paths {
          type uint32;
          description
            "Total number of BGP paths within the context";
        }
        leaf total-prefixes {
          type uint32;
          description
            "Total number of BGP prefixes received within the context";
        }
      }
      container default-route-distance {
        description
          "Administrative distance (or preference) assigned to
           routes received from different sources
           (external, internal, and local).";
        container config {
          description
            "Contains intended configuration";
          leaf external-route-distance {
            type uint8 {
              range "1..255";
            }
            description
              "Administrative distance for routes learned from external
               BGP (eBGP).";
          }
          leaf internal-route-distance {
            type uint8 {
              range "1..255";
            }
            description
              "Administrative distance for routes learned from internal
               BGP (iBGP).";
          }
        }
        container state {
          config false;
          description
            "Contains applied configuration and derived state";
          leaf external-route-distance {
            type uint8 {
              range "1..255";
            }
            description
              "Administrative distance for routes learned from external
               BGP (eBGP).";
          }
          leaf internal-route-distance {
            type uint8 {
              range "1..255";
            }
            description
              "Administrative distance for routes learned from internal
               BGP (iBGP).";
          }
        }
      }
      container confederation {
        description
          "Parameters indicating whether the local system acts as part
           of a BGP confederation";
        container config {
          description
            "Contains intended configuration";
          leaf enabled {
            type boolean;
            description
              "When this leaf is set to true it indicates that
               the local-AS is part of a BGP confederation";
          }
          leaf identifier {
            type inet:as-number;
            description
              "Confederation identifier for the autonomous system.";
          }
          leaf-list member-as {
            type inet:as-number;
            description
              "Remote autonomous systems that are to be treated
               as part of the local confederation.";
          }
        }
        container state {
          config false;
          description
            "Contains applied configuration and derived state";
          leaf enabled {
            type boolean;
            description
              "When this leaf is set to true it indicates that
               the local-AS is part of a BGP confederation";
          }
          leaf identifier {
            type inet:as-number;
            description
              "Confederation identifier for the autonomous system.";
          }
          leaf-list member-as {
            type inet:as-number;
            description
              "Remote autonomous systems that are to be treated
               as part of the local confederation.";
          }
        }
      }
      container graceful-restart {
        description
          "Parameters relating the graceful restart mechanism for BGP";
        container config {
          description
            "Contains intended configuration";
          leaf enabled {
            type boolean;
            description
              "Enable or disable the graceful-restart capability.";
          }
          leaf restart-time {
            type uint16 {
              range "0..4096";
            }
            description
              "Estimated time (in seconds) for the local BGP speaker to
               restart a session. This value is advertise in the graceful
               restart BGP capability.  This is a 12-bit value, referred to
               as Restart Time in RFC4724.  Per RFC4724, the suggested
               default value is <= the hold-time value.";
          }
          leaf stale-routes-time {
            type decimal64 {
              fraction-digits 2;
            }
            description
              "An upper-bound on the time thate stale routes will be
               retained by a router after a session is restarted. If an
               End-of-RIB (EOR) marker is received prior to this timer
               expiring stale-routes will be flushed upon its receipt - if
               no EOR is received, then when this timer expires stale paths
               will be purged. This timer is referred to as the
               Selection_Deferral_Timer in RFC4724";
          }
          leaf helper-only {
            type boolean;
            description
              "Enable graceful-restart in helper mode only. When this leaf
               is set, the local system does not retain forwarding its own
               state during a restart, but supports procedures for the
               receiving speaker, as defined in RFC4724.";
          }
        }
        container state {
          config false;
          description
            "Contains applied configuration and derived state";
          leaf enabled {
            type boolean;
            description
              "Enable or disable the graceful-restart capability.";
          }
          leaf restart-time {
            type uint16 {
              range "0..4096";
            }
            description
              "Estimated time (in seconds) for the local BGP speaker to
               restart a session. This value is advertise in the graceful
               restart BGP capability.  This is a 12-bit value, referred to
               as Restart Time in RFC4724.  Per RFC4724, the suggested
               default value is <= the hold-time value.";
          }
          leaf stale-routes-time {
            type decimal64 {
              fraction-digits 2;
            }
            description
              "An upper-bound on the time thate stale routes will be
               retained by a router after a session is restarted. If an
               End-of-RIB (EOR) marker is received prior to this timer
               expiring stale-routes will be flushed upon its receipt - if
               no EOR is received, then when this timer expires stale paths
               will be purged. This timer is referred to as the
               Selection_Deferral_Timer in RFC4724";
          }
          leaf helper-only {
            type boolean;
            description
              "Enable graceful-restart in helper mode only. When this leaf
               is set, the local system does not retain forwarding its own
               state during a restart, but supports procedures for the
               receiving speaker, as defined in RFC4724.";
          }
        }
      }
      container use-multiple-paths {
        description
          "Parameters related to the use of multiple paths for the
           same NLRI";
        container config {
          description
            "Contains intended configuration";
          leaf enabled {
            type boolean;
            default "false";
            description
              "Whether the use of multiple paths for the same NLRI is
               enabled for the neighbor. This value is overridden by any
               more specific configuration value.";
          }
        }
        container state {
          config false;
          description
            "Contains applied configuration and derived state";
          leaf enabled {
            type boolean;
            default "false";
            description
              "Whether the use of multiple paths for the same NLRI is
               enabled for the neighbor. This value is overridden by any
               more specific configuration value.";
          }
        }
        container ebgp {
          description
            "Multipath parameters for eBGP";
          container config {
            description
              "Contains intended configuration";
            leaf allow-multiple-as {
              type boolean;
              default "false";
              description
                "Allow multipath to use paths from different neighbouring
                 ASes.  The default is to only consider multiple paths
                 from the same neighbouring AS.";
            }
            leaf maximum-paths {
              type uint32;
              default "1";
              description
                "Maximum number of parallel paths to consider when using
                 BGP multipath. The default is use a single path.";
            }
          }
          container state {
            config false;
            description
              "Contains applied configuration and derived state";
            leaf allow-multiple-as {
              type boolean;
              default "false";
              description
                "Allow multipath to use paths from different neighbouring
                 ASes.  The default is to only consider multiple paths
                 from the same neighbouring AS.";
            }
            leaf maximum-paths {
              type uint32;
              default "1";
              description
                "Maximum number of parallel paths to consider when using
                 BGP multipath. The default is use a single path.";
            }
          }
        }
        container ibgp {
          description
            "Multipath parameters for iBGP";
          container config {
            description
              "Contains intended configuration";
            leaf maximum-paths {
              type uint32;
              default "1";
              description
                "Maximum number of parallel paths to consider when using
                 iBGP multipath. The default is to use a single path";
            }
          }
          container state {
            config false;
            description
              "Contains applied configuration and derived state";
            leaf maximum-paths {
              type uint32;
              default "1";
              description
                "Maximum number of parallel paths to consider when using
                 iBGP multipath. The default is to use a single path";
            }
          }
        }
      }
      container route-selection-options {
        description
          "Parameters relating to options for route selection";
        container config {
          description
            "Contains intended configuration";
          leaf always-compare-med {
            type boolean;
            default "false";
            description
              "Compare multi-exit discriminator (MED) value from
               different ASes when selecting the best route.  The default
               behavior is to only compare MEDs for paths received from
               the same AS.";
          }
          leaf ignore-as-path-length {
            type boolean;
            default "false";
            description
              "Ignore the AS path length when selecting the best path.
               The default is to use the AS path length and prefer paths
               with shorter length.";
          }
          leaf external-compare-router-id {
            type boolean;
            default "true";
            description
              "When comparing similar routes received from external BGP
               peers, use the router-id as a criterion to select the
               active path.";
          }
          leaf advertise-inactive-routes {
            type boolean;
            default "false";
            description
              "Advertise inactive routes to external peers.  The default
               is to only advertise active routes.";
          }
          leaf enable-aigp {
            type boolean;
            default "false";
            description
              "Flag to enable sending / receiving accumulated IGP
               attribute in routing updates";
          }
          leaf ignore-next-hop-igp-metric {
            type boolean;
            default "false";
            description
              "Ignore the IGP metric to the next-hop when calculating BGP
               best-path. The default is to select the route for which
               the metric to the next-hop is lowest";
          }
        }
        container state {
          config false;
          description
            "Contains applied configuration and derived state";
          leaf always-compare-med {
            type boolean;
            default "false";
            description
              "Compare multi-exit discriminator (MED) value from
               different ASes when selecting the best route.  The default
               behavior is to only compare MEDs for paths received from
               the same AS.";
          }
          leaf ignore-as-path-length {
            type boolean;
            default "false";
            description
              "Ignore the AS path length when selecting the best path.
               The default is to use the AS path length and prefer paths
               with shorter length.";
          }
          leaf external-compare-router-id {
            type boolean;
            default "true";
            description
              "When comparing similar routes received from external BGP
               peers, use the router-id as a criterion to select the
               active path.";
          }
          leaf advertise-inactive-routes {
            type boolean;
            default "false";
            description
              "Advertise inactive routes to external peers.  The default
               is to only advertise active routes.";
          }
          leaf enable-aigp {
            type boolean;
            default "false";
            description
              "Flag to enable sending / receiving accumulated IGP
               attribute in routing updates";
          }
          leaf ignore-next-hop-igp-metric {
            type boolean;
            default "false";
            description
              "Ignore the IGP metric to the next-hop when calculating BGP
               best-path. The default is to select the route for which
               the metric to the next-hop is lowest";
          }
        }
      }
      container afi-safis {
        description
          "Address family specific configuration";
        list afi-safi {
          leaf afi-safi-name {
            type leafref {
              path "../config/afi-safi-name";
            }
            description
              "Structural leafref to equivalent leaf in ./config container";
          }
          key "afi-safi-name";
          description
            "AFI,SAFI configuration available for the
             neighbour or group";
          container config {
            description
              "Contains intended configuration";
            leaf afi-safi-name {
              type identityref {
                base bgp-types:AFI_SAFI_TYPE;
              }
              description
                "AFI,SAFI";
            }
            leaf enabled {
              type boolean;
              default "false";
              description
                "This leaf indicates whether the IPv4 Unicast AFI,SAFI is
                 enabled for the neighbour or group";
            }
          }
          container state {
            config false;
            description
              "Contains applied configuration and derived state";
            leaf afi-safi-name {
              type identityref {
                base bgp-types:AFI_SAFI_TYPE;
              }
              description
                "AFI,SAFI";
            }
            leaf enabled {
              type boolean;
              default "false";
              description
                "This leaf indicates whether the IPv4 Unicast AFI,SAFI is
                 enabled for the neighbour or group";
            }
            leaf total-paths {
              type uint32;
              description
                "Total number of BGP paths within the context";
            }
            leaf total-prefixes {
              type uint32;
              description
                "Total number of BGP prefixes received within the context";
            }
          }
          container graceful-restart {
            description
              "Parameters relating to BGP graceful-restart";
            container config {
              description
                "Contains intended configuration";
              leaf enabled {
                type boolean;
                default "false";
                description
                  "This leaf indicates whether graceful-restart is enabled for
                   this AFI-SAFI";
              }
            }
            container state {
              config false;
              description
                "Contains applied configuration and derived state";
              leaf enabled {
                type boolean;
                default "false";
                description
                  "This leaf indicates whether graceful-restart is enabled for
                   this AFI-SAFI";
              }
            }
          }
          container route-selection-options {
            description
              "Parameters relating to options for route selection";
            container config {
              description
                "Contains intended configuration";
              leaf always-compare-med {
                type boolean;
                default "false";
                description
                  "Compare multi-exit discriminator (MED) value from
                   different ASes when selecting the best route.  The default
                   behavior is to only compare MEDs for paths received from
                   the same AS.";
              }
              leaf ignore-as-path-length {
                type boolean;
                default "false";
                description
                  "Ignore the AS path length when selecting the best path.
                   The default is to use the AS path length and prefer paths
                   with shorter length.";
              }
              leaf external-compare-router-id {
                type boolean;
                default "true";
                description
                  "When comparing similar routes received from external BGP
                   peers, use the router-id as a criterion to select the
                   active path.";
              }
              leaf advertise-inactive-routes {
                type boolean;
                default "false";
                description
                  "Advertise inactive routes to external peers.  The default
                   is to only advertise active routes.";
              }
              leaf enable-aigp {
                type boolean;
                default "false";
                description
                  "Flag to enable sending / receiving accumulated IGP
                   attribute in routing updates";
              }
              leaf ignore-next-hop-igp-metric {
                type boolean;
                default "false";
                description
                  "Ignore the IGP metric to the next-hop when calculating BGP
                   best-path. The default is to select the route for which
                   the metric to the next-hop is lowest";
              }
            }
            container state {
              config false;
              description
                "Contains applied configuration and derived state";
              leaf always-compare-med {
                type boolean;
                default "false";
                description
                  "Compare multi-exit discriminator (MED) value from
                   different ASes when selecting the best route.  The default
                   behavior is to only compare MEDs for paths received from
                   the same AS.";
              }
              leaf ignore-as-path-length {
                type boolean;
                default "false";
                description
                  "Ignore the AS path length when selecting the best path.
                   The default is to use the AS path length and prefer paths
                   with shorter length.";
              }
              leaf external-compare-router-id {
                type boolean;
                default "true";
                description
                  "When comparing similar routes received from external BGP
                   peers, use the router-id as a criterion to select the
                   active path.";
              }
              leaf advertise-inactive-routes {
                type boolean;
                default "false";
                description
                  "Advertise inactive routes to external peers.  The default
                   is to only advertise active routes.";
              }
              leaf enable-aigp {
                type boolean;
                default "false";
                description
                  "Flag to enable sending / receiving accumulated IGP
                   attribute in routing updates";
              }
              leaf ignore-next-hop-igp-metric {
                type boolean;
                default "false";
                description
                  "Ignore the IGP metric to the next-hop when calculating BGP
                   best-path. The default is to select the route for which
                   the metric to the next-hop is lowest";
              }
            }
          }
          container use-multiple-paths {
            description
              "Parameters related to the use of multiple paths for the
               same NLRI";
            container config {
              description
                "Contains intended configuration";
              leaf enabled {
                type boolean;
                default "false";
                description
                  "Whether the use of multiple paths for the same NLRI is
                   enabled for the neighbor. This value is overridden by any
                   more specific configuration value.";
              }
            }
            container state {
              config false;
              description
                "Contains applied configuration and derived state";
              leaf enabled {
                type boolean;
                default "false";
                description
                  "Whether the use of multiple paths for the same NLRI is
                   enabled for the neighbor. This value is overridden by any
                   more specific configuration value.";
              }
            }
            container ebgp {
              description
                "Multipath parameters for eBGP";
              container config {
                description
                  "Contains intended configuration";
                leaf allow-multiple-as {
                  type boolean;
                  default "false";
                  description
                    "Allow multipath to use paths from different neighbouring
                     ASes.  The default is to only consider multiple paths
                     from the same neighbouring AS.";
                }
                leaf maximum-paths {
                  type uint32;
                  default "1";
                  description
                    "Maximum number of parallel paths to consider when using
                     BGP multipath. The default is use a single path.";
                }
              }
              container state {
                config false;
                description
                  "Contains applied configuration and derived state";
                leaf allow-multiple-as {
                  type boolean;
                  default "false";
                  description
                    "Allow multipath to use paths from different neighbouring
                     ASes.  The default is to only consider multiple paths
                     from the same neighbouring AS.";
                }
                leaf maximum-paths {
                  type uint32;
                  default "1";
                  description
                    "Maximum number of parallel paths to consider when using
                     BGP multipath. The default is use a single path.";
                }
              }
            }
            container ibgp {
              description
                "Multipath parameters for iBGP";
              container config {
                description
                  "Contains intended configuration";
                leaf maximum-paths {
                  type uint32;
                  default "1";
                  description
                    "Maximum number of parallel paths to consider when using
                     iBGP multipath. The default is to use a single path";
                }
              }
              container state {
                config false;
                description
                  "Contains applied configuration and derived state";
                leaf maximum-paths {
                  type uint32;
                  default "1";
                  description
                    "Maximum number of parallel paths to consider when using
                     iBGP multipath. The default is to use a single path";
                }
              }
            }
          }
          container apply-policy {
            description
              "Anchor point for routing policies in the model.
               Import and export policies are with respect to the local
               routing table, i.e., export (send) and import (receive),
               depending on the context.";
            container config {
              description
                "Contains intended configuration";
              leaf-list import-policy {
                type leafref {
                  path "/rpol:routing-policy/rpol:policy-definitions/rpol:policy-definition/rpol:name";
                }
                ordered-by user;
                description
                  "list of policy names in sequence to be applied on
                   receiving a routing update in the current context, e.g.,
                   for the current peer group, neighbor, address family,
                   etc.";
              }
              leaf default-import-policy {
                type rpol:default-policy-type;
                default "REJECT_ROUTE";
                description
                  "explicitly set a default policy if no policy definition
                   in the import policy chain is satisfied.";
              }
              leaf-list export-policy {
                type leafref {
                  path "/rpol:routing-policy/rpol:policy-definitions/rpol:policy-definition/rpol:name";
                }
                ordered-by user;
                description
                  "list of policy names in sequence to be applied on
                   sending a routing update in the current context, e.g.,
                   for the current peer group, neighbor, address family,
                   etc.";
              }
              leaf default-export-policy {
                type rpol:default-policy-type;
                default "REJECT_ROUTE";
                description
                  "explicitly set a default policy if no policy definition
                   in the export policy chain is satisfied.";
              }
            }
            container state {
              config false;
              description
                "Contains applied configuration and derived state";
              leaf-list import-policy {
                type leafref {
                  path "/rpol:routing-policy/rpol:policy-definitions/rpol:policy-definition/rpol:name";
                }
                ordered-by user;
                description
                  "list of policy names in sequence to be applied on
                   receiving a routing update in the current context, e.g.,
                   for the current peer group, neighbor, address family,
                   etc.";
              }
              leaf default-import-policy {
                type rpol:default-policy-type;
                default "REJECT_ROUTE";
                description
                  "explicitly set a default policy if no policy definition
                   in the import policy chain is satisfied.";
              }
              leaf-list export-policy {
                type leafref {
                  path "/rpol:routing-policy/rpol:policy-definitions/rpol:policy-definition/rpol:name";
                }
                ordered-by user;
                description
                  "list of policy names in sequence to be applied on
                   sending a routing update in the current context, e.g.,
                   for the current peer group, neighbor, address family,
                   etc.";
              }
              leaf default-export-policy {
                type rpol:default-policy-type;
                default "REJECT_ROUTE";
                description
                  "explicitly set a default policy if no policy definition
                   in the export policy chain is satisfied.";
              }
            }
          }
          container ipv4-unicast {
            when "../afi-safi-name = 'bgp-types:IPV4_UNICAST'" {
              description
                "Include this container for IPv4 Unicast specific
                 configuration";
            }
            description
              "IPv4 unicast configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
            container config {
              description
                "Contains intended configuration";
              leaf send-default-route {
                type boolean;
                default "false";
                description
                  "If set to true, send the default-route to the neighbour(s)";
              }
            }
            container state {
              config false;
              description
                "Contains applied configuration and derived state";
              leaf send-default-route {
                type boolean;
                default "false";
                description
                  "If set to true, send the default-route to the neighbour(s)";
              }
            }
          }
          container ipv6-unicast {
            when "../afi-safi-name = 'bgp-types:IPV6_UNICAST'" {
              description
                "Include this container for IPv6 Unicast specific
                 configuration";
            }
            description
              "IPv6 unicast configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
            container config {
              description
                "Contains intended configuration";
              leaf send-default-route {
                type boolean;
                default "false";
                description
                  "If set to true, send the default-route to the neighbour(s)";
              }
            }
            container state {
              config false;
              description
                "Contains applied configuration and derived state";
              leaf send-default-route {
                type boolean;
                default "false";
                description
                  "If set to true, send the default-route to the neighbour(s)";
              }
            }
          }
          container ipv4-labeled-unicast {
            when "../afi-safi-name = 'bgp-types:IPV4_LABELED_UNICAST'" {
              description
                "Include this container for IPv4 Labeled Unicast specific
                 configuration";
            }
            description
              "IPv4 Labeled Unicast configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container ipv6-labeled-unicast {
            when "../afi-safi-name = 'bgp-types:IPV6_LABELED_UNICAST'" {
              description
                "Include this container for IPv6 Labeled Unicast specific
                 configuration";
            }
            description
              "IPv6 Labeled Unicast configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container l3vpn-ipv4-unicast {
            when "../afi-safi-name = 'bgp-types:L3VPN_IPV4_UNICAST'" {
              description
                "Include this container for IPv4 Unicast L3VPN specific
                 configuration";
            }
            description
              "Unicast IPv4 L3VPN configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container l3vpn-ipv6-unicast {
            when "../afi-safi-name = 'bgp-types:L3VPN_IPV6_UNICAST'" {
              description
                "Include this container for unicast IPv6 L3VPN specific
                 configuration";
            }
            description
              "Unicast IPv6 L3VPN configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container l3vpn-ipv4-multicast {
            when "../afi-safi-name = 'bgp-types:L3VPN_IPV4_MULTICAST'" {
              description
                "Include this container for multicast IPv6 L3VPN specific
                 configuration";
            }
            description
              "Multicast IPv4 L3VPN configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container l3vpn-ipv6-multicast {
            when "../afi-safi-name = 'bgp-types:L3VPN_IPV6_MULTICAST'" {
              description
                "Include this container for multicast IPv6 L3VPN specific
                 configuration";
            }
            description
              "Multicast IPv6 L3VPN configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container l2vpn-vpls {
            when "../afi-safi-name = 'bgp-types:L2VPN_VPLS'" {
              description
                "Include this container for BGP-signalled VPLS specific
                 configuration";
            }
            description
              "BGP-signalled VPLS configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
          container l2vpn-evpn {
            when "../afi-safi-name = 'bgp-types:L2VPN_EVPN'" {
              description
                "Include this container for BGP EVPN specific
                 configuration";
            }
            description
              "BGP EVPN configuration options";
            container prefix-limit {
              description
                "Parameters relating to the prefix limit for the AFI-SAFI";
              container config {
                description
                  "Contains intended configuration";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
              container state {
                config false;
                description
                  "Contains applied configuration and derived state";
                leaf max-prefixes {
                  type uint32;
                  description
                    "Maximum number of prefixes that will be accepted from the
                     neighbour";
                }
                leaf shutdown-threshold-pct {
                  type bgp-types:percentage;
                  description
                    "Threshold on number of prefixes that can be received from
                     a neighbour before generation of warning messages or log
                     entries. Expressed as a percentage of max-prefixes";
                }
                leaf restart-timer {
                  type decimal64 {
                    fraction-digits 2;
                  }
                  units "seconds";
                  description
                    "Time interval in seconds after which the BGP session is
                     re-established after being torn down due to exceeding the
                     max-prefix limit.";
                }
              }
            }
          }
        }
      }
      container apply-policy {
        description
          "Anchor point for routing policies in the model.
           Import and export policies are with respect to the local
           routing table, i.e., export (send) and import (receive),
           depending on the context.";
        container config {
          description
            "Contains intended configuration";
          leaf-list import-policy {
            type leafref {
              path "/rpol:routing-policy/rpol:policy-definitions/rpol:policy-definition/rpol:name";
            }
            ordered-by user;
            description
              "list of policy names in sequence to be applied on
               receiving a routing update in the current context, e.g.,
               for the current peer group, neighbor, address family,
               etc.";
          }
          leaf default-import-policy {
            type rpol:default-policy-type;
            default "REJECT_ROUTE";
            description
              "explicitly set a default policy if no policy definition
               in the import policy chain is satisfied.";
          }
          leaf-list export-policy {
            type leafref {
              path "/rpol:routing-policy/rpol:policy-definitions/rpol:policy-definition/rpol:name";
            }
            ordered-by user;
            description
              "list of policy names in sequence to be applied on
               sending a routing update in the current context, e.g.,
               for the current peer group, neighbor, address family,
               etc.";
          }
          leaf default-export-policy {
            type rpol:default-policy-type;
            default "REJECT_ROUTE";
            description
              "explicitly set a default policy if no policy definition
               in the export policy chain is satisfied.";
          }
        }
        container state {
          config false;
          description
            "Contains applied configuration and derived state";
          leaf-list import-policy {
            type leafref {
              path "/rpol:routing-policy/rpol:policy-definitions/rpol:policy-definition/rpol:name";
            }
            ordered-by user;
            description
              "list of policy names in sequence to be applied on
               receiving a routing update in the current context, e.g.,
               for the current peer group, neighbor, address family,
               etc.";
          }
          leaf default-import-policy {
            type rpol:default-policy-type;
            default "REJECT_ROUTE";
            description
              "explicitly set a default policy if no policy definition
               in the import policy chain is satisfied.";
          }
          leaf-list export-policy {
            type leafref {
              path "/rpol:routing-policy/rpol:policy-definitions/rpol:policy-definition/rpol:name";
            }
            ordered-by user;
            description
              "list of policy names in sequence to be applied on
               sending a routing update in the current context, e.g.,
               for the current peer group, neighbor, address family,
               etc.";
          }
          leaf default-export-policy {
            type rpol:default-policy-type;
            default "REJECT_ROUTE";
            description
              "explicitly set a default policy if no policy definition
               in the export policy chain is satisfied.";
          }
        }
      }
    }
    container neighbors {
      description
        "Configuration for BGP neighbors";
      list neighbor {
        leaf neighbor-address {
          type leafref {
            path "../config/neighbor-address";
          }
          description
            "Structural leafref to equivalent leaf in ./config container";
        }
        key "neighbor-address";
        description
          "List of BGP neighbors configured on the local system,
           uniquely identified by peer IPv[46] address";
        container config {
          description
            "Contains intended configuration";
          leaf peer-group {
            type leafref {
              path "../../../../peer-groups/peer-group/peer-group-name";
            }
            description
              "The peer-group with which this neighbor is associated";
          }
          leaf neighbor-address {
            type inet:ip-address;
            description
              "Address of the BGP peer, either in IPv4 or IPv6";
          }
          leaf enabled {
            type boolean;
            default "true";
            description
              "Whether the BGP peer is enabled. In cases where the enabled
               leaf is set to false, the local system should not initiate
               connections to the neighbor, and should not respond to TCP
               connections attempts from the neighbor. If the state of the
               BGP session is ESTABLISHED at the time that this leaf is set
               to false, the BGP session should be ceased.";
          }
          leaf peer-as {
            type inet:as-number;
            description
              "AS number of the peer.";
          }
          leaf local-as {
            type inet:as-number;
            description
              "The local autonomous system number that is to be used when
               establishing sessions with the remote peer or peer group, if
               this differs from the global BGP router autonomous system
               number.";
          }
          leaf peer-type {
            type bgp-types:peer-type;
            description
              "Explicitly designate the peer or peer group as internal
               (iBGP) or external (eBGP).";
          }
          leaf auth-password {
            type string;
            description
              "Configures an MD5 authentication password for use with
               neighboring devices.";
          }
          leaf remove-private-as {
            type bgp-types:remove-private-as-option;
            description
              "Remove private AS numbers from updates sent to peers - when
               this leaf is not specified, the AS_PATH attribute should be
               sent to the peer unchanged";
          }
          leaf route-flap-damping {
            type boolean;
            default "false";
            description
              "Enable route flap damping.";
          }
          leaf send-community {
            type bgp-types:community-type;
            default "NONE";
            description
              "Specify which types of community should be sent to the
               neighbor or group. The default is to not send the community
               attribute";
          }
          leaf description {
            type string;
            description
              "An optional textual description (intended primarily for use
               with a peer or group";
          }
        }
        container state {
          config false;
          description
            "Contains applied configuration and derived state";
          leaf peer-group {
            type leafref {
              path "../../../../peer-groups/peer-group/peer-group-name";
            }
            description
              "The peer-group with which this neighbor is associated";
          }
          leaf neighbor-address {
            type inet:ip-address;
            description
              "Address of the BGP peer, either in IPv4 or IPv6";
          }
          leaf enabled {
            type boolean;
            default "true";
            description
              "Whether the BGP peer is enabled. In cases where the enabled
               leaf is set to false, the local system should not initiate
               connections to the neighbor, and should not respond to TCP
               connections attempts from the neighbor. If the state of the
               BGP session is ESTABLISHED at the time that this leaf is set
               to false, the BGP session should be ceased.";
          }
          leaf peer-as {
            type inet:as-number;
            description
              "AS number of the peer.";
          }
          leaf local-as {
            type inet:as-number;
            description
              "The local autonomous system number that is to be used when
               establishing sessions with the remote peer or peer group, if
               this differs from the global BGP router autonomous system
               number.";
          }
          leaf peer-type {
            type bgp-types:peer-type;
            description
              "Explicitly designate the peer or peer group as internal
               (iBGP) or external (eBGP).";
          }
          leaf auth-password {
            type string;
            description
              "Configures an MD5 authentication password for use with
               neighboring devices.";
          }
          leaf remove-private-as {
            type bgp-types:remove-private-as-option;
            description
              "Remove private AS numbers from updates sent to peers - when
               this leaf is not specified, the AS_PATH attribute should be
               sent to the peer unchanged";
          }
          leaf route-flap-damping {
            type boolean;
            default "false";
            description
              "Enable route flap damping.";
          }
          leaf send-community {
            type bgp-types:community-type;
            default "NONE";
            description
              "Specify which types of community should be sent to the
               neighbor or group. The default is to not send the community
               attribute";
          }
          leaf description {
            type string;
            description
              "An optional textual description (intended primarily for use
               with a peer or group";
          }
          leaf session-state {
            type enumeration {
              enum "IDLE" {
                description
                  "neighbor is down, and in the Idle state of the FSM";
              }
              enum "CONNECT" {
                description
                  "neighbor is down, and the session is waiting for the
                   underlying transport session to be established";
              }
              enum "ACTIVE" {
                description
                  "neighbor is down, and the local system is awaiting a
                   conncetion from the remote peer";
              }
              enum "OPENSENT" {
                description
                  "neighbor is in the process of being established.  The
                   local system has sent an OPEN message";
              }
              enum "OPENCONFIRM" {
                description
                  "neighbor is in the process of being established.  The
                   local system is awaiting a NOTIFICATION or KEEPALIVE
                   message";
              }
              enum "ESTABLISHED" {
                description
                  "neighbor is up - the BGP session with the peer is
                   established";
              }
            }
            description
              "Operational state of the BGP peer";
          }
          leaf last-established {
            type uint64;
            description
              "This timestamp indicates the time that the BGP session last
               transitioned in or out of the Established state.  The value
               is the timestamp in seconds relative to the Unix Epoch (Jan
               1, 1970 00:00:00 UTC).
               
               The BGP session uptime can be computed by clients as the
               difference between this value and the current time in UTC
               (assuming the session is in the ESTABLISHED state, per the
               session-state leaf).";
          }
          leaf established-transitions {
            type yang:counter64;
            description
              "Number of transitions to the Established state for the
               neighbor session.  This value is analogous to the
               bgpPeerFsmEstablishedTransitions object from the standard
               BGP-4 MIB";
            reference "RFC 4273 - Definitions of Managed Objects for BGP-4";
          }
          leaf-list supported-capabilities {
            type identityref {
              base bgp-types:BGP_CAPABILITY;
            }
            description
              "BGP capabilities negotiated as supported with the peer";
          }
          leaf UPDATE {
            type uint64;
            description
              "Number of BGP UPDATE messages announcing, withdrawing or
               modifying paths exchanged.";
          }
          leaf NOTIFICATION {
            type uint64;
            description
              "Number of BGP NOTIFICATION messages indicating an error
               condition has occurred exchanged.";
          }
          leaf UPDATE {
            type uint64;
            description
              "Number of BGP UPDATE messages announcing, withdrawing or
               modifying paths exchanged.";
          }
          leaf NOTIFICATION {
            type uint64;
            description
              "Number of BGP NOTIFICATION messages indicating an error
               condition has occurred exchanged.";
          }
          container messages {
            description
              "Counters for BGP messages sent and received from the
               neighbor";
            container sent {
              description
                "Counters relating to BGP messages sent to the neighbor";
            }
            container received {
              description
                "Counters for BGP messages received from the neighbor";
            }
          }
          leaf input {
            type uint32;
            description
              "The number of messages received from the peer currently
               queued";
          }
          leaf output {
            type uint32;
            description
              "The number of messages queued to be sent to the peer";
          }
          container queues {
            description
              "Counters related to queued messages associated with the BGP
               neighbor";
          }
        }
        container timers {
          description
            "Timers related to a BGP neighbor";
          container config {
            description
              "Contains intended configuration";
            leaf connect-retry {
              type decimal64 {
                fraction-digits 2;
              }
              default "30";
              description
                "Time interval in seconds between attempts to establish a
                 session with the peer.";
            }
            leaf hold-time {
              type decimal64 {
                fraction-digits 2;
              }
              default "90";
              description
                "Time interval in seconds that a BGP session will be
                 considered active in the absence of keepalive or other
                 messages from the peer.  The hold-time is typically set to
                 3x the keepalive-interval.";
              reference "RFC 4271 - A Border Gateway Protocol 4, Sec. 10";
            }
            leaf keepalive-interval {
              type decimal64 {
                fraction-digits 2;
              }
              default "30";
              description
                "Time interval in seconds between transmission of keepalive
                 messages to the neighbor.  Typically set to 1/3 the
                 hold-time.";
            }
            leaf minimum-advertisement-interval {
              type decimal64 {
                fraction-digits 2;
              }
              default "30";
              description
                "Minimum time which must elapse between subsequent UPDATE
                 messages relating to a common set of NLRI being transmitted
                 to a peer. This timer is referred to as
                 MinRouteAdvertisementIntervalTimer by RFC 4721 and serves to
                 reduce the number of UPDATE messages transmitted when a
                 particular set of NLRI exhibit instability.";
              reference "RFC 4271 - A Border Gateway Protocol 4, Sec 9.2.1.1";
            }
          }
          container state {
            config false;
            description
              "Contains applied configuration and derived state";
            leaf connect-retry {
              type decimal64 {
                fraction-digits 2;
              }
              default "30";
              description
                "Time interval in seconds between attempts to establish a
                 session with the peer.";
            }
            leaf hold-time {
              type decimal64 {
                fraction-digits 2;
              }
              default "90";
              description
                "Time interval in seconds that a BGP session will be
                 considered active in the absence of keepalive or other
                 messages from the peer.  The hold-time is typically set to
                 3x the keepalive-interval.";
              reference "RFC 4271 - A Border Gateway Protocol 4, Sec. 10";
            }
            leaf keepalive-interval {
              type decimal64 {
                fraction-digits 2;
              }
              default "30";
              description
                "Time interval in seconds between transmission of keepalive
                 messages to the neighbor.  Typically set to 1/3 the
                 hold-time.";
            }
            leaf minimum-advertisement-interval {
              type decimal64 {
                fraction-digits 2;
              }
              default "30";
              description
                "Minimum time which must elapse between subsequent UPDATE
                 messages relating to a common set of NLRI being transmitted
                 to a peer. This timer is referred to as
                 MinRouteAdvertisementIntervalTimer by RFC 4721 and serves to
                 reduce the number of UPDATE messages transmitted when a
                 particular set of NLRI exhibit instability.";
              reference "RFC 4271 - A Border Gateway Protocol 4, Sec 9.2.1.1";
            }
            leaf negotiated-hold-time {
              type decimal64 {
                fraction-digits 2;
              }
              description
                "The negotiated hold-time for the BGP session";
            }
          }
        }
        container transport {
          description
            "Transport session parameters for the BGP neighbor";
          container config {
            description
              "Contains intended configuration";
            leaf tcp-mss {
              type uint16;
              description
                "Sets the max segment size for BGP TCP sessions.";
            }
            leaf mtu-discovery {
              type boolean;
              default "false";
              description
                "Turns path mtu discovery for BGP TCP sessions on (true) or
                 off (false)";
            }
            leaf passive-mode {
              type boolean;
              default "false";
              description
                "Wait for peers to issue requests to open a BGP session,
                 rather than initiating sessions from the local router.";
            }
            leaf local-address {
              type union {
                type inet:ip-address;
                type string;
              }
              description
                "Set the local IP (either IPv4 or IPv6) address to use for
                 the session when sending BGP update messages.  This may be
                 expressed as either an IP address or reference to the name
                 of an interface.";
            }
          }
          container state {
            config false;
            description
              "Contains applied configuration and derived state";
            leaf tcp-mss {
              type uint16;
              description
                "Sets the max segment size for BGP TCP sessions.";
            }
            leaf mtu-discovery {
              type boolean;
              default "false";
              description
                "Turns path mtu discovery for BGP TCP sessions on (true) or
                 off (false)";
            }
            leaf passive-mode {
              type boolean;
              default "false";
              description
                "Wait for peers to issue requests to open a BGP session,
                 rather than initiating sessions from the local router.";
            }
            leaf local-address {
              type union {
                type inet:ip-address;
                type string;
              }
              description
                "Set the local IP (either IPv4 or IPv6) address to use for
                 the session when sending BGP update messages.  This may be
                 expressed as either an IP address or reference to the name
                 of an interface.";
            }
            leaf local-port {
              type inet:port-number;
              description
                "Local TCP port being used for the TCP session supporting
                 the BGP session";
            }
            leaf remote-address {
              type inet:ip-address;
              description
                "Remote address to which the BGP session has been
                 established";
            }
            leaf remote-port {
              type inet:port-number;
              description
                "Remote port being used by the peer for the TCP session
                 supporting the BGP session";
            }
          }
        }
        container error-handling {
          description
            "Error handling parameters used for the BGP neighbor or
             group";
          container config {
            description
              "Contains intended configuration";
            leaf treat-as-withdraw {
              type boolean;
              default "false";
              description
                "Specify whether erroneous UPDATE messages for which the NLRI
                 can be extracted are reated as though the NLRI is withdrawn
                 - avoiding session reset";
              reference "draft-ietf-idr-error-handling-16";
            }
          }
          container state {
            config false;
            description
              "Contains applied configuration and derived state";
            leaf treat-as-withdraw {
              type boolean;
              default "false";
              description
                "Specify whether erroneous UPDATE messages for which the NLRI
                 can be extracted are reated as though the NLRI is withdrawn
                 - avoiding session reset";
              reference "draft-ietf-idr-error-handling-16";
            }
            leaf erroneous-update-messages {
              type uint32;
              description
                "The number of BGP UPDATE messages for which the
                 treat-as-withdraw mechanism has been applied based on
                 erroneous message contents";
            }
          }
        }
        container graceful-restart {
          description
            "Parameters relating the graceful restart mechanism for BGP";
          container config {
            description
              "Contains intended configuration";
            leaf enabled {
              type boolean;
              description
                "Enable or disable the graceful-restart capability.";
            }
            leaf restart-time {
              type uint16 {
                range "0..4096";
              }
              description
                "Estimated time (in seconds) for the local BGP speaker to
                 restart a session. This value is advertise in the graceful
                 restart BGP capability.  This is a 12-bit value, referred to
                 as Restart Time in RFC4724.  Per RFC4724, the suggested
                 default value is <= the hold-time value.";
            }
            leaf stale-routes-time {
              type decimal64 {
                fraction-digits 2;
              }
              description
                "An upper-bound on the time thate stale routes will be
                 retained by a router after a session is restarted. If an
                 End-of-RIB (EOR) marker is received prior to this timer
                 expiring stale-routes will be flushed upon its receipt - if
                 no EOR is received, then when this timer expires stale paths
                 will be purged. This timer is referred to as the
                 Selection_Deferral_Timer in RFC4724";
            }
            leaf helper-only {
              type boolean;
              description
                "Enable graceful-restart in helper mode only. When this leaf
                 is set, the local system does not retain forwarding its own
                 state during a restart, but supports procedures for the
                 receiving speaker, as defined in RFC4724.";
            }
          }
          container state {
            config false;
            description
              "Contains applied configuration and derived state";
            leaf enabled {
              type boolean;
              description
                "Enable or disable the graceful-restart capability.";
            }
            leaf restart-time {
              type uint16 {
                range "0..4096";
              }
              description
                "Estimated time (in seconds) for the local BGP speaker to
                 restart a session. This value is advertise in the graceful
                 restart BGP capability.  This is a 12-bit value, referred to
                 as Restart Time in RFC4724.  Per RFC4724, the suggested
                 default value is <= the hold-time value.";
            }
            leaf stale-routes-time {
              type decimal64 {
                fraction-digits 2;
              }
              description
                "An upper-bound on the time thate stale routes will be
                 retained by a router after a session is restarted. If an
                 End-of-RIB (EOR) marker is received prior to this timer
                 expiring stale-routes will be flushed upon its receipt - if
                 no EOR is received, then when this timer expires stale paths
                 will be purged. This timer is referred to as the
                 Selection_Deferral_Timer in RFC4724";
            }
            leaf helper-only {
              type boolean;
              description
                "Enable graceful-restart in helper mode only. When this leaf
                 is set, the local system does not retain forwarding its own
                 state during a restart, but supports procedures for the
                 receiving speaker, as defined in RFC4724.";
            }
            leaf peer-restart-time {
              type uint16 {
                range "0..4096";
              }
              description
                "The period of time (advertised by the peer) that the peer
                 expects a restart of a BGP session to take";
            }
            leaf peer-restarting {
              type boolean;
              description
                "This flag indicates whether the remote neighbor is
                 currently in the process of restarting, and hence received
                 routes are currently stale";
            }
            leaf local-restarting {
              type boolean;
              description
                "This flag indicates whether the local neighbor is
                 currently restarting. The flag is unset after all NLRI
                 have been advertised to the peer, and the End-of-RIB (EOR)
                 marker has been unset";
            }
            leaf mode {
              type enumeration {
                enum "HELPER_ONLY" {
                  description
                    "The local router is operating in helper-only mode, and
                     hence will not retain forwarding state during a local
                     session restart, but will do so during a restart of
                     the remote peer";
                }
                enum "BILATERAL" {
                  description
                    "The local router is operating in both helper mode, and
                     hence retains forwarding state during a remote
                     restart, and also maintains forwarding state during
                     local session restart";
                }
                enum "REMOTE_HELPER" {
                  description
                    "The local system is able to retain routes during
                     restart but the remote system is only able to act as a
                     helper";
                }
              }
              description
                "This leaf indicates the mode of operation of BGP graceful
                 restart with the peer";
            }
          }
        }
        container logging-options {
          description
            "Logging options for events related to the BGP neighbor or
             group";
          container config {
            description
              "Contains intended configuration";
            leaf log-neighbor-state-changes {
              type boolean;
              default "true";
              description
                "Configure logging of peer state changes.  Default is to
                 enable logging of peer state changes.";
            }
          }
          container state {
            config false;
            description
              "Contains applied configuration and derived state";
            leaf log-neighbor-state-changes {
              type boolean;
              default "true";
              description
                "Configure logging of peer state changes.  Default is to
                 enable logging of peer state changes.";
            }
          }
        }
        container ebgp-multihop {
          description
            "eBGP multi-hop parameters for the BGPgroup";
          container config {
            description
              "Contains intended configuration";
            leaf enabled {
              type boolean;
              default "false";
              description
                "When enabled the referenced group or neighbors are
                 permitted to be indirectly connected - including cases
                 where the TTL can be decremented between the BGP peers";
            }
            leaf multihop-ttl {
              type uint8;
              description
                "Time-to-live value to use when packets are sent to the
                 referenced group or neighbors and ebgp-multihop is
                 enabled";
            }
          }
          container state {
            config false;
            description
              "Contains applied configuration and derived state";
            leaf enabled {
              type boolean;
              default "false";
              description
                "When enabled the referenced group or neighbors are
                 permitted to be indirectly connected - including cases
                 where the TTL can be decremented between the BGP peers";
            }
            leaf multihop-ttl {
              type uint8;
              description
                "Time-to-live value to use when packets are sent to the
                 referenced group or neighbors and ebgp-multihop is
                 enabled";
            }
          }
        }
        container route-reflector {
          description
            "Route reflector parameters for the BGPgroup";
          container config {
            description
              "Contains intended configuration";
            leaf route-reflector-cluster-id {
              type bgp-types:rr-cluster-id-type;
              description
                "route-reflector cluster id to use when local router is
                 configured as a route reflector.  Commonly set at the
                 group level, but allows a different cluster id to be set
                 for each neighbor.";
            }
            leaf route-reflector-client {
              type boolean;
              default "false";
              description
                "Configure the neighbor as a route reflector client.";
            }
          }
          container state {
            config false;
            description
              "Contains applied configuration and derived state";
            leaf route-reflector-cluster-id {
              type bgp-types:rr-cluster-id-type;
              description
                "route-reflector cluster id to use when local router is
                 configured as a route reflector.  Commonly set at the
                 group level, but allows a different cluster id to be set
                 for each neighbor.";
            }
            leaf route-reflector-client {
              type boolean;
              default "false";
              description
                "Configure the neighbor as a route reflector client.";
            }
          }
        }
        container as-path-options {
          description
            "AS_PATH manipulation parameters for the BGP neighbor or
             group";
          container config {
            description
              "Contains intended configuration";
            leaf allow-own-as {
              type uint8;
              default "0";
              description
                "Specify the number of occurrences of the local BGP
                 speaker's AS that can occur within the AS_PATH before it
                 is rejected.";
            }
            leaf replace-peer-as {
              type boolean;
              default "false";
              description
                "Replace occurrences of the peer's AS in the AS_PATH with
                 the local autonomous system number";
            }
          }
          container state {
            config false;
            description
              "Contains applied configuration and derived state";
            leaf allow-own-as {
              type uint8;
              default "0";
              description
                "Specify the number of occurrences of the local BGP
                 speaker's AS that can occur within the AS_PATH before it
                 is rejected.";
            }
            leaf replace-peer-as {
              type boolean;
              default "false";
              description
                "Replace occurrences of the peer's AS in the AS_PATH with
                 the local autonomous system number";
            }
          }
        }
        container add-paths {
          description
            "Parameters relating to the advertisement and receipt of
             multiple paths for a single NLRI (add-paths)";
          container config {
            description
              "Contains intended configuration";
            leaf receive {
              type boolean;
              default "false";
              description
                "Enable ability to receive multiple path advertisements for
                 an NLRI from the neighbor or group";
            }
            leaf send-max {
              type uint8;
              description
                "The maximum number of paths to advertise to neighbors for
                 a single NLRI";
            }
            leaf eligible-prefix-policy {
              type leafref {
                path "/rpol:routing-policy/rpol:policy-definitions/rpol:policy-definition/rpol:name";
              }
              description
                "A reference to a routing policy which can be used to
                 restrict the prefixes for which add-paths is enabled";
            }
          }
          container state {
            config false;
            description
              "Contains applied configuration and derived state";
            leaf receive {
              type boolean;
              default "false";
              description
                "Enable ability to receive multiple path advertisements for
                 an NLRI from the neighbor or group";
            }
            leaf send-max {
              type uint8;
              description
                "The maximum number of paths to advertise to neighbors for
                 a single NLRI";
            }
            leaf eligible-prefix-policy {
              type leafref {
                path "/rpol:routing-policy/rpol:policy-definitions/rpol:policy-definition/rpol:name";
              }
              description
                "A reference to a routing policy which can be used to
                 restrict the prefixes for which add-paths is enabled";
            }
          }
        }
        container use-multiple-paths {
          description
            "Parameters related to the use of multiple-paths for the same
             NLRI when they are received only from this neighbor";
          container config {
            description
              "Contains intended configuration";
            leaf enabled {
              type boolean;
              default "false";
              description
                "Whether the use of multiple paths for the same NLRI is
                 enabled for the neighbor. This value is overridden by any
                 more specific configuration value.";
            }
          }
          container state {
            config false;
            description
              "Contains applied configuration and derived state";
            leaf enabled {
              type boolean;
              default "false";
              description
                "Whether the use of multiple paths for the same NLRI is
                 enabled for the neighbor. This value is overridden by any
                 more specific configuration value.";
            }
          }
          container ebgp {
            description
              "Multipath configuration for eBGP";
            container config {
              description
                "Contains intended configuration";
              leaf allow-multiple-as {
                type boolean;
                default "false";
                description
                  "Allow multipath to use paths from different neighbouring ASes.
                   The default is to only consider multiple paths from the same
                   neighbouring AS.";
              }
            }
            container state {
              config false;
              description
                "Contains applied configuration and derived state";
              leaf allow-multiple-as {
                type boolean;
                default "false";
                description
                  "Allow multipath to use paths from different neighbouring ASes.
                   The default is to only consider multiple paths from the same
                   neighbouring AS.";
              }
            }
          }
        }
        container apply-policy {
          description
            "Anchor point for routing policies in the model.
             Import and export policies are with respect to the local
             routing table, i.e., export (send) and import (receive),
             depending on the context.";
          container config {
            description
              "Contains intended configuration";
            leaf-list import-policy {
              type leafref {
                path "/rpol:routing-policy/rpol:policy-definitions/rpol:policy-definition/rpol:name";
              }
              ordered-by user;
              description
                "list of policy names in sequence to be applied on
                 receiving a routing update in the current context, e.g.,
                 for the current peer group, neighbor, address family,
                 etc.";
            }
            leaf default-import-policy {
              type rpol:default-policy-type;
              default "REJECT_ROUTE";
              description
                "explicitly set a default policy if no policy definition
                 in the import policy chain is satisfied.";
            }
            leaf-list export-policy {
              type leafref {
                path "/rpol:routing-policy/rpol:policy-definitions/rpol:policy-definition/rpol:name";
              }
              ordered-by user;
              description
                "list of policy names in sequence to be applied on
                 sending a routing update in the current context, e.g.,
                 for the current peer group, neighbor, address family,
                 etc.";
            }
            leaf default-export-policy {
              type rpol:default-policy-type;
              default "REJECT_ROUTE";
              description
                "explicitly set a default policy if no policy definition
                 in the export policy chain is satisfied.";
            }
          }
          container state {
            config false;
            description
              "Contains applied configuration and derived state";
            leaf-list import-policy {
              type leafref {
                path "/rpol:routing-policy/rpol:policy-definitions/rpol:policy-definition/rpol:name";
              }
              ordered-by user;
              description
                "list of policy names in sequence to be applied on
                 receiving a routing update in the current context, e.g.,
                 for the current peer group, neighbor, address family,
                 etc.";
            }
            leaf default-import-policy {
              type rpol:default-policy-type;
              default "REJECT_ROUTE";
              description
                "explicitly set a default policy if no policy definition
                 in the import policy chain is satisfied.";
            }
            leaf-list export-policy {
              type leafref {
                path "/rpol:routing-policy/rpol:policy-definitions/rpol:policy-definition/rpol:name";
              }
              ordered-by user;
              description
                "list of policy names in sequence to be applied on
                 sending a routing update in the current context, e.g.,
                 for the current peer group, neighbor, address family,
                 etc.";
            }
            leaf default-export-policy {
              type rpol:default-policy-type;
              default "REJECT_ROUTE";
              description
                "explicitly set a default policy if no policy definition
                 in the export policy chain is satisfied.";
            }
          }
        }
        container afi-safis {
          description
            "Per-address-family configuration parameters associated with
             the neighbor";
          list afi-safi {
            leaf afi-safi-name {
              type leafref {
                path "../config/afi-safi-name";
              }
              description
                "Structural leafref to equivalent leaf in ./config container";
            }
            key "afi-safi-name";
            description
              "AFI,SAFI configuration available for the neighbour or
               group";
            container config {
              description
                "Contains intended configuration";
              leaf afi-safi-name {
                type identityref {
                  base bgp-types:AFI_SAFI_TYPE;
                }
                description
                  "AFI,SAFI";
              }
              leaf enabled {
                type boolean;
                default "false";
                description
                  "This leaf indicates whether the IPv4 Unicast AFI,SAFI is
                   enabled for the neighbour or group";
              }
            }
            container state {
              config false;
              description
                "Contains applied configuration and derived state";
              leaf afi-safi-name {
                type identityref {
                  base bgp-types:AFI_SAFI_TYPE;
                }
                description
                  "AFI,SAFI";
              }
              leaf enabled {
                type boolean;
                default "false";
                description
                  "This leaf indicates whether the IPv4 Unicast AFI,SAFI is
                   enabled for the neighbour or group";
              }
              leaf active {
                type boolean;
                description
                  "This value indicates whether a particular AFI-SAFI has
                   been succesfully negotiated with the peer. An AFI-SAFI may
                   be enabled in the current running configuration, but a
                   session restart may be required in order to negotiate the
                   new capability.";
              }
              leaf received {
                type uint32;
                description
                  "The number of prefixes received from the neighbor";
              }
              leaf sent {
                type uint32;
                description
                  "The number of prefixes advertised to the neighbor";
              }
              leaf installed {
                type uint32;
                description
                  "The number of advertised prefixes installed in the
                   Loc-RIB";
              }
              container prefixes {
                description
                  "Prefix counters for the BGP session";
              }
            }
            container graceful-restart {
              description
                "Parameters relating to BGP graceful-restart";
              container config {
                description
                  "Contains intended configuration";
                leaf enabled {
                  type boolean;
                  default "false";
                  description
                    "This leaf indicates whether graceful-restart is enabled for
                     this AFI-SAFI";
                }
              }
              container state {
                config false;
                description
                  "Contains applied configuration and derived state";
                leaf enabled {
                  type boolean;
                  default "false";
                  description
                    "This leaf indicates whether graceful-restart is enabled for
                     this AFI-SAFI";
                }
                leaf received {
                  type boolean;
                  description
                    "This leaf indicates whether the neighbor advertised the
                     ability to support graceful-restart for this AFI-SAFI";
                }
                leaf advertised {
                  type boolean;
                  description
                    "This leaf indicates whether the ability to support
                     graceful-restart has been advertised to the peer";
                }
              }
            }
            container apply-policy {
              description
                "Anchor point for routing policies in the model.
                 Import and export policies are with respect to the local
                 routing table, i.e., export (send) and import (receive),
                 depending on the context.";
              container config {
                description
                  "Contains intended configuration";
                leaf-list import-policy {
                  type leafref {
                    path "/rpol:routing-policy/rpol:policy-definitions/rpol:policy-definition/rpol:name";
                  }
                  ordered-by user;
                  description
                    "list of policy names in sequence to be applied on
                     receiving a routing update in the current context, e.g.,
                     for the current peer group, neighbor, address family,
                     etc.";
                }
                leaf default-import-policy {
                  type rpol:default-policy-type;
                  default "REJECT_ROUTE";
                  description
                    "explicitly set a default policy if no policy definition
                     in the import policy chain is satisfied.";
                }
                leaf-list export-policy {
                  type leafref {
                    path "/rpol:routing-policy/rpol:policy-definitions/rpol:policy-definition/rpol:name";
                  }
                  ordered-by user;
                  description
                    "list of policy names in sequence to be applied on
                     sending a routing update in the current context, e.g.,
                     for the current peer group, neighbor, address family,
                     etc.";
                }
                leaf default-export-policy {
                  type rpol:default-policy-type;
                  default "REJECT_ROUTE";
                  description
                    "explicitly set a default policy if no policy definition
                     in the export policy chain is satisfied.";
                }
              }
              container state {
                config false;
                description
                  "Contains applied configuration and derived state";
                leaf-list import-policy {
                  type leafref {
                    path "/rpol:routing-policy/rpol:policy-definitions/rpol:policy-definition/rpol:name";
                  }
                  ordered-by user;
                  description
                    "list of policy names in sequence to be applied on
                     receiving a routing update in the current context, e.g.,
                     for the current peer group, neighbor, address family,
                     etc.";
                }
                leaf default-import-policy {
                  type rpol:default-policy-type;
                  default "REJECT_ROUTE";
                  description
                    "explicitly set a default policy if no policy definition
                     in the import policy chain is satisfied.";
                }
                leaf-list export-policy {
                  type leafref {
                    path "/rpol:routing-policy/rpol:policy-definitions/rpol:policy-definition/rpol:name";
                  }
                  ordered-by user;
                  description
                    "list of policy names in sequence to be applied on
                     sending a routing update in the current context, e.g.,
                     for the current peer group, neighbor, address family,
                     etc.";
                }
                leaf default-export-policy {
                  type rpol:default-policy-type;
                  default "REJECT_ROUTE";
                  description
                    "explicitly set a default policy if no policy definition
                     in the export policy chain is satisfied.";
                }
              }
            }
            container ipv4-unicast {
              when "../afi-safi-name = 'bgp-types:IPV4_UNICAST'" {
                description
                  "Include this container for IPv4 Unicast specific
                   configuration";
              }
              description
                "IPv4 unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
              container config {
                description
                  "Contains intended configuration";
                leaf send-default-route {
                  type boolean;
                  default "false";
                  description
                    "If set to true, send the default-route to the neighbour(s)";
                }
              }
              container state {
                config false;
                description
                  "Contains applied configuration and derived state";
                leaf send-default-route {
                  type boolean;
                  default "false";
                  description
                    "If set to true, send the default-route to the neighbour(s)";
                }
              }
            }
            container ipv6-unicast {
              when "../afi-safi-name = 'bgp-types:IPV6_UNICAST'" {
                description
                  "Include this container for IPv6 Unicast specific
                   configuration";
              }
              description
                "IPv6 unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
              container config {
                description
                  "Contains intended configuration";
                leaf send-default-route {
                  type boolean;
                  default "false";
                  description
                    "If set to true, send the default-route to the neighbour(s)";
                }
              }
              container state {
                config false;
                description
                  "Contains applied configuration and derived state";
                leaf send-default-route {
                  type boolean;
                  default "false";
                  description
                    "If set to true, send the default-route to the neighbour(s)";
                }
              }
            }
            container ipv4-labeled-unicast {
              when "../afi-safi-name = 'bgp-types:IPV4_LABELED_UNICAST'" {
                description
                  "Include this container for IPv4 Labeled Unicast specific
                   configuration";
              }
              description
                "IPv4 Labeled Unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container ipv6-labeled-unicast {
              when "../afi-safi-name = 'bgp-types:IPV6_LABELED_UNICAST'" {
                description
                  "Include this container for IPv6 Labeled Unicast specific
                   configuration";
              }
              description
                "IPv6 Labeled Unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv4-unicast {
              when "../afi-safi-name = 'bgp-types:L3VPN_IPV4_UNICAST'" {
                description
                  "Include this container for IPv4 Unicast L3VPN specific
                   configuration";
              }
              description
                "Unicast IPv4 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv6-unicast {
              when "../afi-safi-name = 'bgp-types:L3VPN_IPV6_UNICAST'" {
                description
                  "Include this container for unicast IPv6 L3VPN specific
                   configuration";
              }
              description
                "Unicast IPv6 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv4-multicast {
              when "../afi-safi-name = 'bgp-types:L3VPN_IPV4_MULTICAST'" {
                description
                  "Include this container for multicast IPv6 L3VPN specific
                   configuration";
              }
              description
                "Multicast IPv4 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv6-multicast {
              when "../afi-safi-name = 'bgp-types:L3VPN_IPV6_MULTICAST'" {
                description
                  "Include this container for multicast IPv6 L3VPN specific
                   configuration";
              }
              description
                "Multicast IPv6 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l2vpn-vpls {
              when "../afi-safi-name = 'bgp-types:L2VPN_VPLS'" {
                description
                  "Include this container for BGP-signalled VPLS specific
                   configuration";
              }
              description
                "BGP-signalled VPLS configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l2vpn-evpn {
              when "../afi-safi-name = 'bgp-types:L2VPN_EVPN'" {
                description
                  "Include this container for BGP EVPN specific
                   configuration";
              }
              description
                "BGP EVPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container use-multiple-paths {
              description
                "Parameters related to the use of multiple-paths for the same
                 NLRI when they are received only from this neighbor";
              container config {
                description
                  "Contains intended configuration";
                leaf enabled {
                  type boolean;
                  default "false";
                  description
                    "Whether the use of multiple paths for the same NLRI is
                     enabled for the neighbor. This value is overridden by any
                     more specific configuration value.";
                }
              }
              container state {
                config false;
                description
                  "Contains applied configuration and derived state";
                leaf enabled {
                  type boolean;
                  default "false";
                  description
                    "Whether the use of multiple paths for the same NLRI is
                     enabled for the neighbor. This value is overridden by any
                     more specific configuration value.";
                }
              }
              container ebgp {
                description
                  "Multipath configuration for eBGP";
                container config {
                  description
                    "Contains intended configuration";
                  leaf allow-multiple-as {
                    type boolean;
                    default "false";
                    description
                      "Allow multipath to use paths from different neighbouring ASes.
                       The default is to only consider multiple paths from the same
                       neighbouring AS.";
                  }
                }
                container state {
                  config false;
                  description
                    "Contains applied configuration and derived state";
                  leaf allow-multiple-as {
                    type boolean;
                    default "false";
                    description
                      "Allow multipath to use paths from different neighbouring ASes.
                       The default is to only consider multiple paths from the same
                       neighbouring AS.";
                  }
                }
              }
            }
          }
        }
      }
    }
    container peer-groups {
      description
        "Configuration for BGP peer-groups";
      list peer-group {
        leaf peer-group-name {
          type leafref {
            path "../config/peer-group-name";
          }
          description
            "Structural leafref to equivalent leaf in ./config container";
        }
        key "peer-group-name";
        description
          "List of BGP peer-groups configured on the local system -
           uniquely identified by peer-group name";
        container config {
          description
            "Contains intended configuration";
          leaf peer-group-name {
            type string;
            description
              "Name of the BGP peer-group";
          }
          leaf peer-as {
            type inet:as-number;
            description
              "AS number of the peer.";
          }
          leaf local-as {
            type inet:as-number;
            description
              "The local autonomous system number that is to be used when
               establishing sessions with the remote peer or peer group, if
               this differs from the global BGP router autonomous system
               number.";
          }
          leaf peer-type {
            type bgp-types:peer-type;
            description
              "Explicitly designate the peer or peer group as internal
               (iBGP) or external (eBGP).";
          }
          leaf auth-password {
            type string;
            description
              "Configures an MD5 authentication password for use with
               neighboring devices.";
          }
          leaf remove-private-as {
            type bgp-types:remove-private-as-option;
            description
              "Remove private AS numbers from updates sent to peers - when
               this leaf is not specified, the AS_PATH attribute should be
               sent to the peer unchanged";
          }
          leaf route-flap-damping {
            type boolean;
            default "false";
            description
              "Enable route flap damping.";
          }
          leaf send-community {
            type bgp-types:community-type;
            default "NONE";
            description
              "Specify which types of community should be sent to the
               neighbor or group. The default is to not send the community
               attribute";
          }
          leaf description {
            type string;
            description
              "An optional textual description (intended primarily for use
               with a peer or group";
          }
        }
        container state {
          config false;
          description
            "Contains applied configuration and derived state";
          leaf peer-group-name {
            type string;
            description
              "Name of the BGP peer-group";
          }
          leaf peer-as {
            type inet:as-number;
            description
              "AS number of the peer.";
          }
          leaf local-as {
            type inet:as-number;
            description
              "The local autonomous system number that is to be used when
               establishing sessions with the remote peer or peer group, if
               this differs from the global BGP router autonomous system
               number.";
          }
          leaf peer-type {
            type bgp-types:peer-type;
            description
              "Explicitly designate the peer or peer group as internal
               (iBGP) or external (eBGP).";
          }
          leaf auth-password {
            type string;
            description
              "Configures an MD5 authentication password for use with
               neighboring devices.";
          }
          leaf remove-private-as {
            type bgp-types:remove-private-as-option;
            description
              "Remove private AS numbers from updates sent to peers - when
               this leaf is not specified, the AS_PATH attribute should be
               sent to the peer unchanged";
          }
          leaf route-flap-damping {
            type boolean;
            default "false";
            description
              "Enable route flap damping.";
          }
          leaf send-community {
            type bgp-types:community-type;
            default "NONE";
            description
              "Specify which types of community should be sent to the
               neighbor or group. The default is to not send the community
               attribute";
          }
          leaf description {
            type string;
            description
              "An optional textual description (intended primarily for use
               with a peer or group";
          }
          leaf total-paths {
            type uint32;
            description
              "Total number of BGP paths within the context";
          }
          leaf total-prefixes {
            type uint32;
            description
              "Total number of BGP prefixes received within the context";
          }
        }
        container timers {
          description
            "Timers related to a BGP peer-group";
          container config {
            description
              "Contains intended configuration";
            leaf connect-retry {
              type decimal64 {
                fraction-digits 2;
              }
              default "30";
              description
                "Time interval in seconds between attempts to establish a
                 session with the peer.";
            }
            leaf hold-time {
              type decimal64 {
                fraction-digits 2;
              }
              default "90";
              description
                "Time interval in seconds that a BGP session will be
                 considered active in the absence of keepalive or other
                 messages from the peer.  The hold-time is typically set to
                 3x the keepalive-interval.";
              reference "RFC 4271 - A Border Gateway Protocol 4, Sec. 10";
            }
            leaf keepalive-interval {
              type decimal64 {
                fraction-digits 2;
              }
              default "30";
              description
                "Time interval in seconds between transmission of keepalive
                 messages to the neighbor.  Typically set to 1/3 the
                 hold-time.";
            }
            leaf minimum-advertisement-interval {
              type decimal64 {
                fraction-digits 2;
              }
              default "30";
              description
                "Minimum time which must elapse between subsequent UPDATE
                 messages relating to a common set of NLRI being transmitted
                 to a peer. This timer is referred to as
                 MinRouteAdvertisementIntervalTimer by RFC 4721 and serves to
                 reduce the number of UPDATE messages transmitted when a
                 particular set of NLRI exhibit instability.";
              reference "RFC 4271 - A Border Gateway Protocol 4, Sec 9.2.1.1";
            }
          }
          container state {
            config false;
            description
              "Contains applied configuration and derived state";
            leaf connect-retry {
              type decimal64 {
                fraction-digits 2;
              }
              default "30";
              description
                "Time interval in seconds between attempts to establish a
                 session with the peer.";
            }
            leaf hold-time {
              type decimal64 {
                fraction-digits 2;
              }
              default "90";
              description
                "Time interval in seconds that a BGP session will be
                 considered active in the absence of keepalive or other
                 messages from the peer.  The hold-time is typically set to
                 3x the keepalive-interval.";
              reference "RFC 4271 - A Border Gateway Protocol 4, Sec. 10";
            }
            leaf keepalive-interval {
              type decimal64 {
                fraction-digits 2;
              }
              default "30";
              description
                "Time interval in seconds between transmission of keepalive
                 messages to the neighbor.  Typically set to 1/3 the
                 hold-time.";
            }
            leaf minimum-advertisement-interval {
              type decimal64 {
                fraction-digits 2;
              }
              default "30";
              description
                "Minimum time which must elapse between subsequent UPDATE
                 messages relating to a common set of NLRI being transmitted
                 to a peer. This timer is referred to as
                 MinRouteAdvertisementIntervalTimer by RFC 4721 and serves to
                 reduce the number of UPDATE messages transmitted when a
                 particular set of NLRI exhibit instability.";
              reference "RFC 4271 - A Border Gateway Protocol 4, Sec 9.2.1.1";
            }
          }
        }
        container transport {
          description
            "Transport session parameters for the BGP peer-group";
          container config {
            description
              "Contains intended configuration";
            leaf tcp-mss {
              type uint16;
              description
                "Sets the max segment size for BGP TCP sessions.";
            }
            leaf mtu-discovery {
              type boolean;
              default "false";
              description
                "Turns path mtu discovery for BGP TCP sessions on (true) or
                 off (false)";
            }
            leaf passive-mode {
              type boolean;
              default "false";
              description
                "Wait for peers to issue requests to open a BGP session,
                 rather than initiating sessions from the local router.";
            }
            leaf local-address {
              type union {
                type inet:ip-address;
                type string;
              }
              description
                "Set the local IP (either IPv4 or IPv6) address to use for
                 the session when sending BGP update messages.  This may be
                 expressed as either an IP address or reference to the name
                 of an interface.";
            }
          }
          container state {
            config false;
            description
              "Contains applied configuration and derived state";
            leaf tcp-mss {
              type uint16;
              description
                "Sets the max segment size for BGP TCP sessions.";
            }
            leaf mtu-discovery {
              type boolean;
              default "false";
              description
                "Turns path mtu discovery for BGP TCP sessions on (true) or
                 off (false)";
            }
            leaf passive-mode {
              type boolean;
              default "false";
              description
                "Wait for peers to issue requests to open a BGP session,
                 rather than initiating sessions from the local router.";
            }
            leaf local-address {
              type union {
                type inet:ip-address;
                type string;
              }
              description
                "Set the local IP (either IPv4 or IPv6) address to use for
                 the session when sending BGP update messages.  This may be
                 expressed as either an IP address or reference to the name
                 of an interface.";
            }
          }
        }
        container error-handling {
          description
            "Error handling parameters used for the BGP peer-group";
          container config {
            description
              "Contains intended configuration";
            leaf treat-as-withdraw {
              type boolean;
              default "false";
              description
                "Specify whether erroneous UPDATE messages for which the NLRI
                 can be extracted are reated as though the NLRI is withdrawn
                 - avoiding session reset";
              reference "draft-ietf-idr-error-handling-16";
            }
          }
          container state {
            config false;
            description
              "Contains applied configuration and derived state";
            leaf treat-as-withdraw {
              type boolean;
              default "false";
              description
                "Specify whether erroneous UPDATE messages for which the NLRI
                 can be extracted are reated as though the NLRI is withdrawn
                 - avoiding session reset";
              reference "draft-ietf-idr-error-handling-16";
            }
          }
        }
        container graceful-restart {
          description
            "Parameters relating the graceful restart mechanism for BGP";
          container config {
            description
              "Contains intended configuration";
            leaf enabled {
              type boolean;
              description
                "Enable or disable the graceful-restart capability.";
            }
            leaf restart-time {
              type uint16 {
                range "0..4096";
              }
              description
                "Estimated time (in seconds) for the local BGP speaker to
                 restart a session. This value is advertise in the graceful
                 restart BGP capability.  This is a 12-bit value, referred to
                 as Restart Time in RFC4724.  Per RFC4724, the suggested
                 default value is <= the hold-time value.";
            }
            leaf stale-routes-time {
              type decimal64 {
                fraction-digits 2;
              }
              description
                "An upper-bound on the time thate stale routes will be
                 retained by a router after a session is restarted. If an
                 End-of-RIB (EOR) marker is received prior to this timer
                 expiring stale-routes will be flushed upon its receipt - if
                 no EOR is received, then when this timer expires stale paths
                 will be purged. This timer is referred to as the
                 Selection_Deferral_Timer in RFC4724";
            }
            leaf helper-only {
              type boolean;
              description
                "Enable graceful-restart in helper mode only. When this leaf
                 is set, the local system does not retain forwarding its own
                 state during a restart, but supports procedures for the
                 receiving speaker, as defined in RFC4724.";
            }
          }
          container state {
            config false;
            description
              "Contains applied configuration and derived state";
            leaf enabled {
              type boolean;
              description
                "Enable or disable the graceful-restart capability.";
            }
            leaf restart-time {
              type uint16 {
                range "0..4096";
              }
              description
                "Estimated time (in seconds) for the local BGP speaker to
                 restart a session. This value is advertise in the graceful
                 restart BGP capability.  This is a 12-bit value, referred to
                 as Restart Time in RFC4724.  Per RFC4724, the suggested
                 default value is <= the hold-time value.";
            }
            leaf stale-routes-time {
              type decimal64 {
                fraction-digits 2;
              }
              description
                "An upper-bound on the time thate stale routes will be
                 retained by a router after a session is restarted. If an
                 End-of-RIB (EOR) marker is received prior to this timer
                 expiring stale-routes will be flushed upon its receipt - if
                 no EOR is received, then when this timer expires stale paths
                 will be purged. This timer is referred to as the
                 Selection_Deferral_Timer in RFC4724";
            }
            leaf helper-only {
              type boolean;
              description
                "Enable graceful-restart in helper mode only. When this leaf
                 is set, the local system does not retain forwarding its own
                 state during a restart, but supports procedures for the
                 receiving speaker, as defined in RFC4724.";
            }
          }
        }
        container logging-options {
          description
            "Logging options for events related to the BGP neighbor or
             group";
          container config {
            description
              "Contains intended configuration";
            leaf log-neighbor-state-changes {
              type boolean;
              default "true";
              description
                "Configure logging of peer state changes.  Default is to
                 enable logging of peer state changes.";
            }
          }
          container state {
            config false;
            description
              "Contains applied configuration and derived state";
            leaf log-neighbor-state-changes {
              type boolean;
              default "true";
              description
                "Configure logging of peer state changes.  Default is to
                 enable logging of peer state changes.";
            }
          }
        }
        container ebgp-multihop {
          description
            "eBGP multi-hop parameters for the BGPgroup";
          container config {
            description
              "Contains intended configuration";
            leaf enabled {
              type boolean;
              default "false";
              description
                "When enabled the referenced group or neighbors are
                 permitted to be indirectly connected - including cases
                 where the TTL can be decremented between the BGP peers";
            }
            leaf multihop-ttl {
              type uint8;
              description
                "Time-to-live value to use when packets are sent to the
                 referenced group or neighbors and ebgp-multihop is
                 enabled";
            }
          }
          container state {
            config false;
            description
              "Contains applied configuration and derived state";
            leaf enabled {
              type boolean;
              default "false";
              description
                "When enabled the referenced group or neighbors are
                 permitted to be indirectly connected - including cases
                 where the TTL can be decremented between the BGP peers";
            }
            leaf multihop-ttl {
              type uint8;
              description
                "Time-to-live value to use when packets are sent to the
                 referenced group or neighbors and ebgp-multihop is
                 enabled";
            }
          }
        }
        container route-reflector {
          description
            "Route reflector parameters for the BGPgroup";
          container config {
            description
              "Contains intended configuration";
            leaf route-reflector-cluster-id {
              type bgp-types:rr-cluster-id-type;
              description
                "route-reflector cluster id to use when local router is
                 configured as a route reflector.  Commonly set at the
                 group level, but allows a different cluster id to be set
                 for each neighbor.";
            }
            leaf route-reflector-client {
              type boolean;
              default "false";
              description
                "Configure the neighbor as a route reflector client.";
            }
          }
          container state {
            config false;
            description
              "Contains applied configuration and derived state";
            leaf route-reflector-cluster-id {
              type bgp-types:rr-cluster-id-type;
              description
                "route-reflector cluster id to use when local router is
                 configured as a route reflector.  Commonly set at the
                 group level, but allows a different cluster id to be set
                 for each neighbor.";
            }
            leaf route-reflector-client {
              type boolean;
              default "false";
              description
                "Configure the neighbor as a route reflector client.";
            }
          }
        }
        container as-path-options {
          description
            "AS_PATH manipulation parameters for the BGP neighbor or
             group";
          container config {
            description
              "Contains intended configuration";
            leaf allow-own-as {
              type uint8;
              default "0";
              description
                "Specify the number of occurrences of the local BGP
                 speaker's AS that can occur within the AS_PATH before it
                 is rejected.";
            }
            leaf replace-peer-as {
              type boolean;
              default "false";
              description
                "Replace occurrences of the peer's AS in the AS_PATH with
                 the local autonomous system number";
            }
          }
          container state {
            config false;
            description
              "Contains applied configuration and derived state";
            leaf allow-own-as {
              type uint8;
              default "0";
              description
                "Specify the number of occurrences of the local BGP
                 speaker's AS that can occur within the AS_PATH before it
                 is rejected.";
            }
            leaf replace-peer-as {
              type boolean;
              default "false";
              description
                "Replace occurrences of the peer's AS in the AS_PATH with
                 the local autonomous system number";
            }
          }
        }
        container add-paths {
          description
            "Parameters relating to the advertisement and receipt of
             multiple paths for a single NLRI (add-paths)";
          container config {
            description
              "Contains intended configuration";
            leaf receive {
              type boolean;
              default "false";
              description
                "Enable ability to receive multiple path advertisements for
                 an NLRI from the neighbor or group";
            }
            leaf send-max {
              type uint8;
              description
                "The maximum number of paths to advertise to neighbors for
                 a single NLRI";
            }
            leaf eligible-prefix-policy {
              type leafref {
                path "/rpol:routing-policy/rpol:policy-definitions/rpol:policy-definition/rpol:name";
              }
              description
                "A reference to a routing policy which can be used to
                 restrict the prefixes for which add-paths is enabled";
            }
          }
          container state {
            config false;
            description
              "Contains applied configuration and derived state";
            leaf receive {
              type boolean;
              default "false";
              description
                "Enable ability to receive multiple path advertisements for
                 an NLRI from the neighbor or group";
            }
            leaf send-max {
              type uint8;
              description
                "The maximum number of paths to advertise to neighbors for
                 a single NLRI";
            }
            leaf eligible-prefix-policy {
              type leafref {
                path "/rpol:routing-policy/rpol:policy-definitions/rpol:policy-definition/rpol:name";
              }
              description
                "A reference to a routing policy which can be used to
                 restrict the prefixes for which add-paths is enabled";
            }
          }
        }
        container use-multiple-paths {
          description
            "Parameters related to the use of multiple paths for the
             same NLRI";
          container config {
            description
              "Contains intended configuration";
            leaf enabled {
              type boolean;
              default "false";
              description
                "Whether the use of multiple paths for the same NLRI is
                 enabled for the neighbor. This value is overridden by any
                 more specific configuration value.";
            }
          }
          container state {
            config false;
            description
              "Contains applied configuration and derived state";
            leaf enabled {
              type boolean;
              default "false";
              description
                "Whether the use of multiple paths for the same NLRI is
                 enabled for the neighbor. This value is overridden by any
                 more specific configuration value.";
            }
          }
          container ebgp {
            description
              "Multipath parameters for eBGP";
            container config {
              description
                "Contains intended configuration";
              leaf allow-multiple-as {
                type boolean;
                default "false";
                description
                  "Allow multipath to use paths from different neighbouring
                   ASes.  The default is to only consider multiple paths
                   from the same neighbouring AS.";
              }
              leaf maximum-paths {
                type uint32;
                default "1";
                description
                  "Maximum number of parallel paths to consider when using
                   BGP multipath. The default is use a single path.";
              }
            }
            container state {
              config false;
              description
                "Contains applied configuration and derived state";
              leaf allow-multiple-as {
                type boolean;
                default "false";
                description
                  "Allow multipath to use paths from different neighbouring
                   ASes.  The default is to only consider multiple paths
                   from the same neighbouring AS.";
              }
              leaf maximum-paths {
                type uint32;
                default "1";
                description
                  "Maximum number of parallel paths to consider when using
                   BGP multipath. The default is use a single path.";
              }
            }
          }
          container ibgp {
            description
              "Multipath parameters for iBGP";
            container config {
              description
                "Contains intended configuration";
              leaf maximum-paths {
                type uint32;
                default "1";
                description
                  "Maximum number of parallel paths to consider when using
                   iBGP multipath. The default is to use a single path";
              }
            }
            container state {
              config false;
              description
                "Contains applied configuration and derived state";
              leaf maximum-paths {
                type uint32;
                default "1";
                description
                  "Maximum number of parallel paths to consider when using
                   iBGP multipath. The default is to use a single path";
              }
            }
          }
        }
        container apply-policy {
          description
            "Anchor point for routing policies in the model.
             Import and export policies are with respect to the local
             routing table, i.e., export (send) and import (receive),
             depending on the context.";
          container config {
            description
              "Contains intended configuration";
            leaf-list import-policy {
              type leafref {
                path "/rpol:routing-policy/rpol:policy-definitions/rpol:policy-definition/rpol:name";
              }
              ordered-by user;
              description
                "list of policy names in sequence to be applied on
                 receiving a routing update in the current context, e.g.,
                 for the current peer group, neighbor, address family,
                 etc.";
            }
            leaf default-import-policy {
              type rpol:default-policy-type;
              default "REJECT_ROUTE";
              description
                "explicitly set a default policy if no policy definition
                 in the import policy chain is satisfied.";
            }
            leaf-list export-policy {
              type leafref {
                path "/rpol:routing-policy/rpol:policy-definitions/rpol:policy-definition/rpol:name";
              }
              ordered-by user;
              description
                "list of policy names in sequence to be applied on
                 sending a routing update in the current context, e.g.,
                 for the current peer group, neighbor, address family,
                 etc.";
            }
            leaf default-export-policy {
              type rpol:default-policy-type;
              default "REJECT_ROUTE";
              description
                "explicitly set a default policy if no policy definition
                 in the export policy chain is satisfied.";
            }
          }
          container state {
            config false;
            description
              "Contains applied configuration and derived state";
            leaf-list import-policy {
              type leafref {
                path "/rpol:routing-policy/rpol:policy-definitions/rpol:policy-definition/rpol:name";
              }
              ordered-by user;
              description
                "list of policy names in sequence to be applied on
                 receiving a routing update in the current context, e.g.,
                 for the current peer group, neighbor, address family,
                 etc.";
            }
            leaf default-import-policy {
              type rpol:default-policy-type;
              default "REJECT_ROUTE";
              description
                "explicitly set a default policy if no policy definition
                 in the import policy chain is satisfied.";
            }
            leaf-list export-policy {
              type leafref {
                path "/rpol:routing-policy/rpol:policy-definitions/rpol:policy-definition/rpol:name";
              }
              ordered-by user;
              description
                "list of policy names in sequence to be applied on
                 sending a routing update in the current context, e.g.,
                 for the current peer group, neighbor, address family,
                 etc.";
            }
            leaf default-export-policy {
              type rpol:default-policy-type;
              default "REJECT_ROUTE";
              description
                "explicitly set a default policy if no policy definition
                 in the export policy chain is satisfied.";
            }
          }
        }
        container afi-safis {
          description
            "Per-address-family configuration parameters associated with
             thegroup";
          list afi-safi {
            leaf afi-safi-name {
              type leafref {
                path "../config/afi-safi-name";
              }
              description
                "Structural leafref to equivalent leaf in ./config container";
            }
            key "afi-safi-name";
            description
              "AFI,SAFI configuration available for the
               neighbour or group";
            container config {
              description
                "Contains intended configuration";
              leaf afi-safi-name {
                type identityref {
                  base bgp-types:AFI_SAFI_TYPE;
                }
                description
                  "AFI,SAFI";
              }
              leaf enabled {
                type boolean;
                default "false";
                description
                  "This leaf indicates whether the IPv4 Unicast AFI,SAFI is
                   enabled for the neighbour or group";
              }
            }
            container state {
              config false;
              description
                "Contains applied configuration and derived state";
              leaf afi-safi-name {
                type identityref {
                  base bgp-types:AFI_SAFI_TYPE;
                }
                description
                  "AFI,SAFI";
              }
              leaf enabled {
                type boolean;
                default "false";
                description
                  "This leaf indicates whether the IPv4 Unicast AFI,SAFI is
                   enabled for the neighbour or group";
              }
            }
            container graceful-restart {
              description
                "Parameters relating to BGP graceful-restart";
              container config {
                description
                  "Contains intended configuration";
                leaf enabled {
                  type boolean;
                  default "false";
                  description
                    "This leaf indicates whether graceful-restart is enabled for
                     this AFI-SAFI";
                }
              }
              container state {
                config false;
                description
                  "Contains applied configuration and derived state";
                leaf enabled {
                  type boolean;
                  default "false";
                  description
                    "This leaf indicates whether graceful-restart is enabled for
                     this AFI-SAFI";
                }
              }
            }
            container route-selection-options {
              description
                "Parameters relating to options for route selection";
              container config {
                description
                  "Contains intended configuration";
                leaf always-compare-med {
                  type boolean;
                  default "false";
                  description
                    "Compare multi-exit discriminator (MED) value from
                     different ASes when selecting the best route.  The default
                     behavior is to only compare MEDs for paths received from
                     the same AS.";
                }
                leaf ignore-as-path-length {
                  type boolean;
                  default "false";
                  description
                    "Ignore the AS path length when selecting the best path.
                     The default is to use the AS path length and prefer paths
                     with shorter length.";
                }
                leaf external-compare-router-id {
                  type boolean;
                  default "true";
                  description
                    "When comparing similar routes received from external BGP
                     peers, use the router-id as a criterion to select the
                     active path.";
                }
                leaf advertise-inactive-routes {
                  type boolean;
                  default "false";
                  description
                    "Advertise inactive routes to external peers.  The default
                     is to only advertise active routes.";
                }
                leaf enable-aigp {
                  type boolean;
                  default "false";
                  description
                    "Flag to enable sending / receiving accumulated IGP
                     attribute in routing updates";
                }
                leaf ignore-next-hop-igp-metric {
                  type boolean;
                  default "false";
                  description
                    "Ignore the IGP metric to the next-hop when calculating BGP
                     best-path. The default is to select the route for which
                     the metric to the next-hop is lowest";
                }
              }
              container state {
                config false;
                description
                  "Contains applied configuration and derived state";
                leaf always-compare-med {
                  type boolean;
                  default "false";
                  description
                    "Compare multi-exit discriminator (MED) value from
                     different ASes when selecting the best route.  The default
                     behavior is to only compare MEDs for paths received from
                     the same AS.";
                }
                leaf ignore-as-path-length {
                  type boolean;
                  default "false";
                  description
                    "Ignore the AS path length when selecting the best path.
                     The default is to use the AS path length and prefer paths
                     with shorter length.";
                }
                leaf external-compare-router-id {
                  type boolean;
                  default "true";
                  description
                    "When comparing similar routes received from external BGP
                     peers, use the router-id as a criterion to select the
                     active path.";
                }
                leaf advertise-inactive-routes {
                  type boolean;
                  default "false";
                  description
                    "Advertise inactive routes to external peers.  The default
                     is to only advertise active routes.";
                }
                leaf enable-aigp {
                  type boolean;
                  default "false";
                  description
                    "Flag to enable sending / receiving accumulated IGP
                     attribute in routing updates";
                }
                leaf ignore-next-hop-igp-metric {
                  type boolean;
                  default "false";
                  description
                    "Ignore the IGP metric to the next-hop when calculating BGP
                     best-path. The default is to select the route for which
                     the metric to the next-hop is lowest";
                }
              }
            }
            container use-multiple-paths {
              description
                "Parameters related to the use of multiple paths for the
                 same NLRI";
              container config {
                description
                  "Contains intended configuration";
                leaf enabled {
                  type boolean;
                  default "false";
                  description
                    "Whether the use of multiple paths for the same NLRI is
                     enabled for the neighbor. This value is overridden by any
                     more specific configuration value.";
                }
              }
              container state {
                config false;
                description
                  "Contains applied configuration and derived state";
                leaf enabled {
                  type boolean;
                  default "false";
                  description
                    "Whether the use of multiple paths for the same NLRI is
                     enabled for the neighbor. This value is overridden by any
                     more specific configuration value.";
                }
              }
              container ebgp {
                description
                  "Multipath parameters for eBGP";
                container config {
                  description
                    "Contains intended configuration";
                  leaf allow-multiple-as {
                    type boolean;
                    default "false";
                    description
                      "Allow multipath to use paths from different neighbouring
                       ASes.  The default is to only consider multiple paths
                       from the same neighbouring AS.";
                  }
                  leaf maximum-paths {
                    type uint32;
                    default "1";
                    description
                      "Maximum number of parallel paths to consider when using
                       BGP multipath. The default is use a single path.";
                  }
                }
                container state {
                  config false;
                  description
                    "Contains applied configuration and derived state";
                  leaf allow-multiple-as {
                    type boolean;
                    default "false";
                    description
                      "Allow multipath to use paths from different neighbouring
                       ASes.  The default is to only consider multiple paths
                       from the same neighbouring AS.";
                  }
                  leaf maximum-paths {
                    type uint32;
                    default "1";
                    description
                      "Maximum number of parallel paths to consider when using
                       BGP multipath. The default is use a single path.";
                  }
                }
              }
              container ibgp {
                description
                  "Multipath parameters for iBGP";
                container config {
                  description
                    "Contains intended configuration";
                  leaf maximum-paths {
                    type uint32;
                    default "1";
                    description
                      "Maximum number of parallel paths to consider when using
                       iBGP multipath. The default is to use a single path";
                  }
                }
                container state {
                  config false;
                  description
                    "Contains applied configuration and derived state";
                  leaf maximum-paths {
                    type uint32;
                    default "1";
                    description
                      "Maximum number of parallel paths to consider when using
                       iBGP multipath. The default is to use a single path";
                  }
                }
              }
            }
            container apply-policy {
              description
                "Anchor point for routing policies in the model.
                 Import and export policies are with respect to the local
                 routing table, i.e., export (send) and import (receive),
                 depending on the context.";
              container config {
                description
                  "Contains intended configuration";
                leaf-list import-policy {
                  type leafref {
                    path "/rpol:routing-policy/rpol:policy-definitions/rpol:policy-definition/rpol:name";
                  }
                  ordered-by user;
                  description
                    "list of policy names in sequence to be applied on
                     receiving a routing update in the current context, e.g.,
                     for the current peer group, neighbor, address family,
                     etc.";
                }
                leaf default-import-policy {
                  type rpol:default-policy-type;
                  default "REJECT_ROUTE";
                  description
                    "explicitly set a default policy if no policy definition
                     in the import policy chain is satisfied.";
                }
                leaf-list export-policy {
                  type leafref {
                    path "/rpol:routing-policy/rpol:policy-definitions/rpol:policy-definition/rpol:name";
                  }
                  ordered-by user;
                  description
                    "list of policy names in sequence to be applied on
                     sending a routing update in the current context, e.g.,
                     for the current peer group, neighbor, address family,
                     etc.";
                }
                leaf default-export-policy {
                  type rpol:default-policy-type;
                  default "REJECT_ROUTE";
                  description
                    "explicitly set a default policy if no policy definition
                     in the export policy chain is satisfied.";
                }
              }
              container state {
                config false;
                description
                  "Contains applied configuration and derived state";
                leaf-list import-policy {
                  type leafref {
                    path "/rpol:routing-policy/rpol:policy-definitions/rpol:policy-definition/rpol:name";
                  }
                  ordered-by user;
                  description
                    "list of policy names in sequence to be applied on
                     receiving a routing update in the current context, e.g.,
                     for the current peer group, neighbor, address family,
                     etc.";
                }
                leaf default-import-policy {
                  type rpol:default-policy-type;
                  default "REJECT_ROUTE";
                  description
                    "explicitly set a default policy if no policy definition
                     in the import policy chain is satisfied.";
                }
                leaf-list export-policy {
                  type leafref {
                    path "/rpol:routing-policy/rpol:policy-definitions/rpol:policy-definition/rpol:name";
                  }
                  ordered-by user;
                  description
                    "list of policy names in sequence to be applied on
                     sending a routing update in the current context, e.g.,
                     for the current peer group, neighbor, address family,
                     etc.";
                }
                leaf default-export-policy {
                  type rpol:default-policy-type;
                  default "REJECT_ROUTE";
                  description
                    "explicitly set a default policy if no policy definition
                     in the export policy chain is satisfied.";
                }
              }
            }
            container ipv4-unicast {
              when "../afi-safi-name = 'bgp-types:IPV4_UNICAST'" {
                description
                  "Include this container for IPv4 Unicast specific
                   configuration";
              }
              description
                "IPv4 unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
              container config {
                description
                  "Contains intended configuration";
                leaf send-default-route {
                  type boolean;
                  default "false";
                  description
                    "If set to true, send the default-route to the neighbour(s)";
                }
              }
              container state {
                config false;
                description
                  "Contains applied configuration and derived state";
                leaf send-default-route {
                  type boolean;
                  default "false";
                  description
                    "If set to true, send the default-route to the neighbour(s)";
                }
              }
            }
            container ipv6-unicast {
              when "../afi-safi-name = 'bgp-types:IPV6_UNICAST'" {
                description
                  "Include this container for IPv6 Unicast specific
                   configuration";
              }
              description
                "IPv6 unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
              container config {
                description
                  "Contains intended configuration";
                leaf send-default-route {
                  type boolean;
                  default "false";
                  description
                    "If set to true, send the default-route to the neighbour(s)";
                }
              }
              container state {
                config false;
                description
                  "Contains applied configuration and derived state";
                leaf send-default-route {
                  type boolean;
                  default "false";
                  description
                    "If set to true, send the default-route to the neighbour(s)";
                }
              }
            }
            container ipv4-labeled-unicast {
              when "../afi-safi-name = 'bgp-types:IPV4_LABELED_UNICAST'" {
                description
                  "Include this container for IPv4 Labeled Unicast specific
                   configuration";
              }
              description
                "IPv4 Labeled Unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container ipv6-labeled-unicast {
              when "../afi-safi-name = 'bgp-types:IPV6_LABELED_UNICAST'" {
                description
                  "Include this container for IPv6 Labeled Unicast specific
                   configuration";
              }
              description
                "IPv6 Labeled Unicast configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv4-unicast {
              when "../afi-safi-name = 'bgp-types:L3VPN_IPV4_UNICAST'" {
                description
                  "Include this container for IPv4 Unicast L3VPN specific
                   configuration";
              }
              description
                "Unicast IPv4 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv6-unicast {
              when "../afi-safi-name = 'bgp-types:L3VPN_IPV6_UNICAST'" {
                description
                  "Include this container for unicast IPv6 L3VPN specific
                   configuration";
              }
              description
                "Unicast IPv6 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv4-multicast {
              when "../afi-safi-name = 'bgp-types:L3VPN_IPV4_MULTICAST'" {
                description
                  "Include this container for multicast IPv6 L3VPN specific
                   configuration";
              }
              description
                "Multicast IPv4 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l3vpn-ipv6-multicast {
              when "../afi-safi-name = 'bgp-types:L3VPN_IPV6_MULTICAST'" {
                description
                  "Include this container for multicast IPv6 L3VPN specific
                   configuration";
              }
              description
                "Multicast IPv6 L3VPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l2vpn-vpls {
              when "../afi-safi-name = 'bgp-types:L2VPN_VPLS'" {
                description
                  "Include this container for BGP-signalled VPLS specific
                   configuration";
              }
              description
                "BGP-signalled VPLS configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
            container l2vpn-evpn {
              when "../afi-safi-name = 'bgp-types:L2VPN_EVPN'" {
                description
                  "Include this container for BGP EVPN specific
                   configuration";
              }
              description
                "BGP EVPN configuration options";
              container prefix-limit {
                description
                  "Parameters relating to the prefix limit for the AFI-SAFI";
                container config {
                  description
                    "Contains intended configuration";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
                container state {
                  config false;
                  description
                    "Contains applied configuration and derived state";
                  leaf max-prefixes {
                    type uint32;
                    description
                      "Maximum number of prefixes that will be accepted from the
                       neighbour";
                  }
                  leaf shutdown-threshold-pct {
                    type bgp-types:percentage;
                    description
                      "Threshold on number of prefixes that can be received from
                       a neighbour before generation of warning messages or log
                       entries. Expressed as a percentage of max-prefixes";
                  }
                  leaf restart-timer {
                    type decimal64 {
                      fraction-digits 2;
                    }
                    units "seconds";
                    description
                      "Time interval in seconds after which the BGP session is
                       re-established after being torn down due to exceeding the
                       max-prefix limit.";
                  }
                }
              }
            }
          }
        }
      }
    }
  }
}
