module ietf-bgp-types-state {
  yang-version 1;
  namespace "urn:ietf:params:xml:ns:yang:ietf-bgp-types-state";
  prefix bgp-types-s;

  import ietf-inet-types {
    prefix inet;
  }
  import ietf-bgp-types {
    prefix bgp-types;
  }

  organization
    "OpenConfig working group";
  contact
    "OpenConfig working group
     netopenconfig@googlegroups.com";
  description
    "This module contains general data definitions for use in BGP
     policy. It can be imported by modules that make use of BGP
     attributes";

  revision 2016-06-21 {
    description
      "OpenConfig BGP refactor";
    reference "2.1.1";
  }
}
