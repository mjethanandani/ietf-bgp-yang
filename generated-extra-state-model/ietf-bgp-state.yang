module ietf-bgp-state {
  yang-version 1;
  namespace "urn:ietf:params:xml:ns:yang:ietf-bgp-state";
  prefix bgp-s;

  import ietf-routing-policy {
    prefix rpol;
  }
  import ietf-bgp {
    prefix bgp;
  }
  include ietf-bgp-common-state;
  include ietf-bgp-common-multiprotocol-state;
  include ietf-bgp-common-structure-state;
  include ietf-bgp-peer-group-state;
  include ietf-bgp-neighbor-state;
  include ietf-bgp-global-state;

  organization
    "OpenConfig working group";
  contact
    "OpenConfig working group
     netopenconfig@googlegroups.com";
  description
    "This module describes a YANG model for BGP protocol
     configuration.It is a limited subset of all of the configuration
     parameters available in the variety of vendor implementations,
     hence it is expected that it would be augmented with vendor-
     specific configuration data as needed. Additional modules or
     submodules to handle other aspects of BGP configuration,
     including policy, VRFs, VPNs, and additional address families
     are also expected.
     
     This model supports the following BGP configuration level
     hierarchy:
     
      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]";

  revision 2016-06-21 {
    description
      "OpenConfig BGP refactor";
    reference "2.1.1";
  }
  revision 2016-06-06 {
    description
      "OpenConfig public release";
    reference "2.1.0";
  }
  revision 2016-03-31 {
    description
      "OpenConfig public release";
    reference "2.0.1";
  }

  grouping bgp-top {
    description
      "Top-level grouping for the BGP model data";
    container bgp {
      config false;
      description
        "Top-level configuration and state for the BGP router";
      container global {
        description
          "Global configuration for the BGP router";
        uses bgp-global-base;
        uses rpol:apply-policy-group;
      }
      container neighbors {
        description
          "Configuration for BGP neighbors";
        uses bgp-neighbor-list;
      }
      container peer-groups {
        description
          "Configuration for BGP peer-groups";
        uses bgp-peer-group-list;
      }
    }
  }

  uses bgp-top;
}
