submodule ietf-bgp-global-state {
  belongs-to ietf-bgp-state {
    prefix bgp-s;
  }

  import ietf-inet-types {
    prefix inet;
  }
  import ietf-yang-types {
    prefix yang;
  }
  include ietf-bgp-common-state;
  include ietf-bgp-common-multiprotocol-state;

  organization
    "OpenConfig working group";
  contact
    "OpenConfig working group
     netopenconfig@googlegroups.com";
  description
    "This sub-module contains groupings that are specific to the
     global context of the OpenConfig BGP module";

  revision 2016-06-21 {
    description
      "OpenConfig BGP refactor";
    reference "2.1.1";
  }

  grouping bgp-global-config {
    description
      "Global configuration options for the BGP router.";
    leaf as {
      type inet:as-number;
      mandatory true;
      description
        "Local autonomous system number of the router.  Uses
         the 32-bit as-number type from the model in RFC 6991.";
    }
    leaf router-id {
      type yang:dotted-quad;
      description
        "Router id of the router - an unsigned 32-bit integer
         expressed in dotted quad notation.";
      reference
        "RFC4271 - A Border Gateway Protocol 4 (BGP-4),
         Section 4.2";
    }
  }

  grouping bgp-global-state {
    description
      "Operational state parameters for the BGP neighbor";
    uses bgp-common-state;
  }

  grouping bgp-global-default-route-distance-config {
    description
      "Configuration options relating to the administrative distance
       (or preference) assigned to routes received from different
       sources (external, internal, and local).";
    leaf external-route-distance {
      type uint8 {
        range "1..255";
      }
      description
        "Administrative distance for routes learned from external
         BGP (eBGP).";
    }
    leaf internal-route-distance {
      type uint8 {
        range "1..255";
      }
      description
        "Administrative distance for routes learned from internal
         BGP (iBGP).";
    }
  }

  grouping bgp-global-confederation-config {
    description
      "Configuration options specifying parameters when the local
       router is within an autonomous system which is part of a BGP
       confederation.";
    leaf enabled {
      type boolean;
      description
        "When this leaf is set to true it indicates that
         the local-AS is part of a BGP confederation";
    }
    leaf identifier {
      type inet:as-number;
      description
        "Confederation identifier for the autonomous system.";
    }
    leaf-list member-as {
      type inet:as-number;
      config false;
      description
        "Remote autonomous systems that are to be treated
         as part of the local confederation.";
    }
  }

  grouping bgp-global-afi-safi-list {
    description
      "List of address-families associated with the BGP instance";
    list afi-safi {
      key "afi-safi-name";
      config false;
      description
        "AFI,SAFI configuration available for the
         neighbour or group";
      uses bgp-common-mp-afi-safi-config;
      uses bgp-common-state;
      container graceful-restart {
        description
          "Parameters relating to BGP graceful-restart";
        uses bgp-common-mp-afi-safi-graceful-restart-config;
      }
      uses bgp-common-route-selection-options;
      uses bgp-common-global-group-use-multiple-paths;
      uses bgp-common-mp-all-afi-safi-list-contents;
    }
  }

  grouping bgp-global-base {
    description
      "Global configuration parameters for the BGP router";
    uses bgp-global-config;
    uses bgp-global-state;
    container default-route-distance {
      config false;
      description
        "Administrative distance (or preference) assigned to
         routes received from different sources
         (external, internal, and local).";
      uses bgp-global-default-route-distance-config;
    }
    container confederation {
      config false;
      description
        "Parameters indicating whether the local system acts as part
         of a BGP confederation";
      uses bgp-global-confederation-config;
    }
    container graceful-restart {
      config false;
      description
        "Parameters relating the graceful restart mechanism for BGP";
      uses bgp-common-graceful-restart-config;
    }
    uses bgp-common-global-group-use-multiple-paths;
    uses bgp-common-route-selection-options;
    container afi-safis {
      config false;
      description
        "Address family specific configuration";
      uses bgp-global-afi-safi-list;
    }
  }
}
