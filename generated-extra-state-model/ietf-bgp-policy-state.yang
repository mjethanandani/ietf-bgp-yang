module ietf-bgp-policy-state {
  yang-version 1;
  namespace "urn:ietf:params:xml:ns:yang:ietf-bgp-policy-state";
  prefix bgp-pol-s;

  import ietf-inet-types {
    prefix inet;
  }
  import ietf-routing-policy {
    prefix rpol;
  }
  import ietf-policy-types {
    prefix pol-types;
  }
  import ietf-bgp-types {
    prefix bgp-types;
  }
  import ietf-bgp-policy {
    prefix bgp-pol;
  }

  organization
    "OpenConfig working group";
  contact
    "OpenConfig working group
     netopenconfig@googlegroups.com";
  description
    "This module contains data definitions for BGP routing policy.
     It augments the base routing-policy module with BGP-specific
     options for conditions and actions.";

  revision 2016-06-21 {
    description
      "OpenConfig BGP refactor";
    reference "2.1.1";
  }

  grouping match-community-top {
    description
      "Top-level grouping for match conditions on communities";
    container match-community-set {
      config false;
      description
        "Top-level container for match conditions on communities.
         Match a referenced community-set according to the logic
         defined in the match-set-options leaf";
      leaf community-set {
        type leafref {
          path "/rpol:routing-policy/rpol:defined-sets/bgp-pol:bgp-defined-sets/bgp-pol:community-sets/bgp-pol:community-set/bgp-pol:community-set-name";
        }
        description
          "References a defined community set";
      }
      uses rpol:match-set-options-group;
    }
  }

  grouping match-ext-community-top {
    description
      "Top-level grouping for match conditions on extended
       communities";
    container match-ext-community-set {
      config false;
      description
        "Match a referenced extended community-set according to the
         logic defined in the match-set-options leaf";
      leaf ext-community-set {
        type leafref {
          path "/rpol:routing-policy/rpol:defined-sets/bgp-pol:bgp-defined-sets/bgp-pol:ext-community-sets/bgp-pol:ext-community-set/bgp-pol:ext-community-set-name";
        }
        description
          "References a defined extended community set";
      }
      uses rpol:match-set-options-group;
    }
  }

  grouping match-as-path-top {
    description
      "Top-level grouping for match conditions on AS path set";
    container match-as-path-set {
      config false;
      description
        "Match a referenced as-path set according to the logic
         defined in the match-set-options leaf";
      leaf as-path-set {
        type leafref {
          path "/rpol:routing-policy/rpol:defined-sets/bgp-pol:bgp-defined-sets/bgp-pol:as-path-sets/bgp-pol:as-path-set/bgp-pol:as-path-set-name";
        }
        description
          "References a defined AS path set";
      }
      uses rpol:match-set-options-group;
    }
  }

  grouping bgp-match-set-conditions {
    description
      "Condition statement definitions for checking membership in a
       defined set";
    uses match-community-top;
    uses match-ext-community-top;
    uses match-as-path-top;
  }

  grouping community-count-top {
    description
      "Top-level grouping for community count condition";
    container community-count {
      config false;
      description
        "Value and comparison operations for conditions based on the
         number of communities in the route update";
      uses pol-types:attribute-compare-operators;
    }
  }

  grouping as-path-length-top {
    description
      "Top-level grouping for AS path length condition";
    container as-path-length {
      config false;
      description
        "Value and comparison operations for conditions based on the
         length of the AS path in the route update";
      uses pol-types:attribute-compare-operators;
    }
  }

  grouping bgp-conditions-top {
    description
      "Top-level grouping for BGP-specific policy conditions";
    container bgp-conditions {
      config false;
      description
        "Top-level container ";
      leaf med-eq {
        type uint32;
        description
          "Condition to check if the received MED value is equal to
           the specified value";
      }
      leaf origin-eq {
        type bgp-types:bgp-origin-attr-type;
        description
          "Condition to check if the route origin is equal to the
           specified value";
      }
      leaf-list next-hop-in {
        type inet:ip-address-no-zone;
        description
          "List of next hop addresses to check for in the route
           update";
      }
      leaf-list afi-safi-in {
        type identityref {
          base bgp-types:AFI_SAFI_TYPE;
        }
        description
          "List of address families which the NLRI may be within";
      }
      leaf local-pref-eq {
        type uint32;
        description
          "Condition to check if the local pref attribute is equal to
           the specified value";
      }
      leaf route-type {
        type enumeration {
          enum "INTERNAL" {
            description
              "route type is internal";
          }
          enum "EXTERNAL" {
            description
              "route type is external";
          }
        }
        description
          "Condition to check the route type in the route update";
      }
      uses community-count-top;
      uses as-path-length-top;
      uses bgp-match-set-conditions;
    }
  }

  grouping community-set-top {
    description
      "Top-level grouping for BGP community sets";
    container community-sets {
      config false;
      description
        "Enclosing container for list of defined BGP community sets";
      list community-set {
        key "community-set-name";
        description
          "List of defined BGP community sets";
        leaf community-set-name {
          type string;
          mandatory true;
          description
            "name / label of the community set -- this is used to
             reference the set in match conditions";
        }
        leaf-list community-member {
          type union {
            type bgp-types:bgp-std-community-type;
            type bgp-types:bgp-community-regexp-type;
            type bgp-types:bgp-well-known-community-type;
          }
          description
            "members of the community set";
        }
      }
    }
  }

  grouping ext-community-set-top {
    description
      "Top-level grouping for extended BGP community sets";
    container ext-community-sets {
      config false;
      description
        "Enclosing container for list of extended BGP community
         sets";
      list ext-community-set {
        key "ext-community-set-name";
        description
          "List of defined extended BGP community sets";
        leaf ext-community-set-name {
          type string;
          description
            "name / label of the extended community set -- this is
             used to reference the set in match conditions";
        }
        leaf-list ext-community-member {
          type union {
            type bgp-types:bgp-ext-community-type;
            type bgp-types:bgp-community-regexp-type;
          }
          description
            "members of the extended community set";
        }
      }
    }
  }

  grouping as-path-set-top {
    description
      "Top-level grouping for AS path sets";
    container as-path-sets {
      config false;
      description
        "Enclosing container for list of define AS path sets";
      list as-path-set {
        key "as-path-set-name";
        description
          "List of defined AS path sets";
        leaf as-path-set-name {
          type string;
          description
            "name of the AS path set -- this is used to reference the
             set in match conditions";
        }
        leaf-list as-path-set-member {
          type string;
          description
            "AS path expression -- list of ASes in the set";
        }
      }
    }
  }

  grouping as-path-prepend-top {
    description
      "Top-level grouping for the AS path prepend action";
    container set-as-path-prepend {
      config false;
      description
        "action to prepend local AS number to the AS-path a
         specified number of times";
      leaf repeat-n {
        type uint8 {
          range "1..max";
        }
        description
          "Number of times to prepend the local AS number to the AS
           path.  The value should be between 1 and the maximum
           supported by the implementation.";
      }
    }
  }

  grouping set-community-action-common {
    description
      "Common leaves for set-community and set-ext-community
       actions";
    leaf method {
      type enumeration {
        enum "INLINE" {
          description
            "The extended communities are specified inline as a
             list";
        }
        enum "REFERENCE" {
          description
            "The extended communities are specified by referencing a
             defined ext-community set";
        }
      }
      description
        "Indicates the method used to specify the extended
         communities for the set-ext-community action";
    }
    leaf options {
      type bgp-pol:bgp-set-community-option-type;
      description
        "Options for modifying the community attribute with
         the specified values.  These options apply to both
         methods of setting the community attribute.";
    }
  }

  grouping set-community-inline-top {
    description
      "Top-level grouping or inline specification of set-community
       action";
    container inline {
      config false;
      description
        "Set the community values for the action inline with
         a list.";
      leaf-list communities {
        type union {
          type bgp-types:bgp-std-community-type;
          type bgp-types:bgp-well-known-community-type;
        }
        description
          "Set the community values for the update inline with a
           list.";
      }
    }
  }

  grouping set-community-reference-top {
    description
      "Top-level grouping for referening a community-set in the
       set-community action";
    container reference {
      config false;
      description
        "Provide a reference to a defined community set for the
         set-community action";
      leaf community-set-ref {
        type leafref {
          path "/rpol:routing-policy/rpol:defined-sets/bgp-pol:bgp-defined-sets/bgp-pol:community-sets/bgp-pol:community-set/bgp-pol:community-set-name";
        }
        description
          "References a defined community set by name";
      }
    }
  }

  grouping set-community-action-top {
    description
      "Top-level grouping for the set-community action";
    container set-community {
      config false;
      description
        "Action to set the community attributes of the route, along
         with options to modify how the community is modified.
         Communities may be set using an inline list OR
         reference to an existing defined set (not both).";
      uses set-community-action-common;
      uses set-community-inline-top;
      uses set-community-reference-top;
    }
  }

  grouping set-ext-community-inline-top {
    description
      "Top-level grouping or inline specification of
       set-ext-community action";
    container inline {
      config false;
      description
        "Set the extended community values for the action inline with
         a list.";
      leaf-list communities {
        type union {
          type bgp-types:bgp-ext-community-type;
          type bgp-types:bgp-well-known-community-type;
        }
        description
          "Set the extended community values for the update inline
           with a list.";
      }
    }
  }

  grouping set-ext-community-reference-top {
    description
      "Top-level grouping for referening an extended community-set
       in the set-community action";
    container reference {
      config false;
      description
        "Provide a reference to an extended community set for the
         set-ext-community action";
      leaf ext-community-set-ref {
        type leafref {
          path "/rpol:routing-policy/rpol:defined-sets/bgp-pol:bgp-defined-sets/bgp-pol:ext-community-sets/bgp-pol:ext-community-set/bgp-pol:ext-community-set-name";
        }
        description
          "References a defined extended community set by name";
      }
    }
  }

  grouping set-ext-community-action-top {
    description
      "Top-level grouping for the set-ext-community action";
    container set-ext-community {
      config false;
      description
        "Action to set the extended community attributes of the
         route, along with options to modify how the community is
         modified. Extended communities may be set using an inline
         list OR a reference to an existing defined set (but not
         both).";
      uses set-community-action-common;
      uses set-ext-community-inline-top;
      uses set-ext-community-reference-top;
    }
  }

  grouping bgp-actions-top {
    description
      "Top-level grouping for BGP-specific actions";
    container bgp-actions {
      config false;
      description
        "Top-level container for BGP-specific actions";
      leaf set-route-origin {
        type bgp-types:bgp-origin-attr-type;
        description
          "set the origin attribute to the specified value";
      }
      leaf set-local-pref {
        type uint32;
        description
          "set the local pref attribute on the route update";
      }
      leaf set-next-hop {
        type bgp-pol:bgp-next-hop-type;
        description
          "set the next-hop attribute in the route update";
      }
      leaf set-med {
        type bgp-pol:bgp-set-med-type;
        description
          "set the med metric attribute in the route update";
      }
      uses as-path-prepend-top;
      uses set-community-action-top;
      uses set-ext-community-action-top;
    }
  }

  augment "/rpol:routing-policy/rpol:defined-sets" {
    description
      "adds BGP defined sets container to routing policy
       model";
    container bgp-defined-sets {
      description
        "BGP-related set definitions for policy match conditions";
      uses community-set-top;
      uses ext-community-set-top;
      uses as-path-set-top;
    }
  }
  augment "/rpol:routing-policy/rpol:policy-definitions/rpol:policy-definition/rpol:statements/rpol:statement/rpol:conditions" {
    description
      "BGP policy conditions added to routing policy module";
    uses bgp-conditions-top;
  }
  augment "/rpol:routing-policy/rpol:policy-definitions/rpol:policy-definition/rpol:statements/rpol:statement/rpol:actions" {
    description
      "BGP policy actions added to routing policy
       module";
    uses bgp-actions-top;
  }
}
